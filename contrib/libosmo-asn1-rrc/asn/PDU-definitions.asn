PDU-definitions DEFINITIONS AUTOMATIC TAGS ::=

BEGIN

--**************************************************************
--
-- IE parameter types from other modules
--
--**************************************************************

IMPORTS

-- Core Network IEs :
	CN-DomainIdentity,
	CN-InformationInfo,
	CN-InformationInfo-r6,
	CN-InformationInfoFull,
	NAS-Message,
	PagingRecordTypeID,
	PLMN-Identity,
-- UTRAN Mobility IEs :
	CellIdentity,
	CellIdentity-PerRL-List,
	DedicatedPriorityInformation,
	DedicatedPriorityInformation-r11,
	URA-Identity,
-- User Equipment IEs :
	AccessStratumReleaseIndicator,
	ActivationTime,
	C-RNTI,
	CapabilityUpdateRequirement,
	CapabilityUpdateRequirement-r4,
	CapabilityUpdateRequirement-r4-ext,
	CapabilityUpdateRequirement-r5,
	CapabilityUpdateRequirement-v770ext,
	CapabilityUpdateRequirement-v860ext,
	CapabilityUpdateRequirement-r7,
	CapabilityUpdateRequirement-r8,
	CellUpdateCause,
	CellUpdateCause-ext,
	CipheringAlgorithm,
	CipheringAlgorithm-r7,
	CipheringModeInfo,
	CipheringModeInfo-r7,
	DelayRestrictionFlag,
	DL-PhysChCapabilityFDD-v380ext,
	DSCH-RNTI,
	E-RNTI,
	EstablishmentCause,
	ExtendedWaitTime,
	FailureCauseWithProtErr,
	FailureCauseWithProtErrTrId,
	FrequencyBandsIndicatorSupport,
	GroupReleaseInformation,
	H-RNTI,
	High-MobilityDetected,
	InitialUE-Identity,
	IntegrityProtActivationInfo,
	IntegrityProtectionModeInfo,
	IntegrityProtectionModeInfo-r7,
	N-308,
	PagingCause,
	PagingRecordList,
	PagingRecord2List-r5,
	PDCP-Capability-r4-ext,
	PDCP-Capability-v770ext,
	Pre-RedirectionInfo,
	ProtocolErrorIndicator,
	ProtocolErrorIndicatorWithMoreInfo,
	RadioFrequencyBandTDDList,
	Rb-timer-indicator,
	RedirectionInfo,
	RedirectionInfo-r6,
	RedirectionInfo-v860ext,
	RejectionCause,
	ReleaseCause,
	RF-CapabBandListFDDComp-ext2,
	RF-CapabilityComp,
	RRC-StateIndicator,
	RRC-TransactionIdentifier,
	RSR-VCC-Info,
	SecurityCapability,
	SR-VCC-Info,
	SR-VCC-SecurityRABInfo-v860ext,
	START-Value,
	STARTList,
	SystemSpecificCapUpdateReq-v590ext,
	U-RNTI,
	U-RNTI-Short,
	UESpecificBehaviourInformation1idle,
	UESpecificBehaviourInformation1interRAT,
	UE-CapabilityContainer-IEs,
	UE-ConnTimersAndConstants,
	UE-ConnTimersAndConstants-v3a0ext,
	UE-ConnTimersAndConstants-v860ext,
	UE-ConnTimersAndConstants-r5,
	UE-ConnTimersAndConstants-r11,
	UE-HSPA-Identities-r6,
	UE-RadioAccessCapabBandFDDList2,
	UE-RadioAccessCapabBandFDDList-ext,
	UE-RadioAccessCapabBand-va40ext,
	UE-RadioAccessCapability,
	UE-RadioAccessCapability-v370ext,
	UE-RadioAccessCapability-v380ext,
	UE-RadioAccessCapability-v3a0ext,
	UE-RadioAccessCapability-v3g0ext,
	UE-RadioAccessCapability-v4b0ext,
	UE-RadioAccessCapability-v590ext,
	UE-RadioAccessCapability-v5c0ext,
	UE-RadioAccessCapability-v650ext,
	UE-RadioAccessCapability-v680ext,
	UE-RadioAccessCapability-v7e0ext,
	UE-RadioAccessCapability-v7f0ext,
	UE-RadioAccessCapability-v860ext,
	UE-RadioAccessCapability-v880ext,
	UE-RadioAccessCapability-v890ext,
	UE-RadioAccessCapability-v920ext,
	UE-RadioAccessCapability-va40ext,
	UE-RadioAccessCapability-va80ext,
	UE-RadioAccessCapability-va60ext,
	UE-RadioAccessCapability-vb50ext,
	UE-RadioAccessCapabilityComp,
	UE-RadioAccessCapabilityComp-ext,
	UE-RadioAccessCapabilityComp-v770ext,
	UE-RadioAccessCapabilityComp2,
	UE-RadioAccessCapabilityComp2-v770ext,
	UE-RadioAccessCapabilityComp2-v7f0ext,
	UE-RadioAccessCapabilityComp2-v860ext,
	UE-RadioAccessCapabilityComp2-v920ext,
	UE-RadioAccessCapabilityComp2-va40ext, 
	UE-RadioAccessCapabilityComp2-vb50ext,
	UE-RadioAccessCapabilityComp-TDD128,
	UE-RadioAccessCapabilityInfo-v770ext,
	UE-RadioAccessCapabilityInfo-TDD128-v8b0ext,
	UE-RadioAccessCapabilityInfo-TDD128-vb50ext,
	UE-SecurityInformation,
	UE-SecurityInformation2,
	UE-SpecificCapabilityInformation-LCRTDD,
	URA-UpdateCause,
	UTRAN-DRX-CycleLengthCoefficient,
	UTRAN-DRX-CycleLengthCoefficient-r7,
	WaitTime,
-- Radio Bearer IEs :
	DefaultConfigIdentity,
	DefaultConfigIdentity-r4,
	DefaultConfigIdentity-r5,
	DefaultConfigIdentity-r6,
	DefaultConfigForCellFACH,
	DefaultConfigMode,
	DL-CounterSynchronisationInfo,
	DL-CounterSynchronisationInfo-r5,
	PDCP-ROHC-TargetMode,
	PredefinedConfigIdentity,
	PredefinedConfigStatusList,
	PredefinedConfigStatusListComp,
	PredefinedConfigSetWithDifferentValueTag,
	RAB-Info,
	RAB-Info-r6,
	RAB-Info-r7,
	RAB-Info-Post,
	RAB-InformationList,
	RAB-InformationList-r6,
	RAB-InformationReconfigList,
	RAB-InformationReconfigList-r8,
	RAB-InformationMBMSPtpList,
	RAB-InformationSetup-r7,
	RAB-InformationSetup-r8,
	RAB-InformationSetup-v820ext,
	RAB-InformationSetup-r11,
	RAB-InformationSetupList,
	RAB-InformationSetupList-r4,
	RAB-InformationSetupList-r5,
	RAB-InformationSetupList-r6-ext,
	RAB-InformationSetupList-r6,
	RAB-InformationSetupList-v6b0ext,
	RAB-InformationSetupList-r7,
	RAB-InformationSetupList-r8,
	RAB-InformationSetupList-v820ext,
	RAB-InformationSetupList-r11,
	RB-ActivationTimeInfoList,
	RB-COUNT-C-InformationList,
	RB-COUNT-C-MSB-InformationList,
	RB-IdentityList,
	RB-InformationAffectedList,
	RB-InformationAffectedList-r5,
	RB-InformationAffectedList-r6,
	RB-InformationAffectedList-r7,
	RB-InformationAffectedList-r8,
	RB-InformationChangedList-r6,
	RB-InformationReconfigList,
	RB-InformationReconfigList-r4,
	RB-InformationReconfigList-r5,
	RB-InformationReconfigList-r6,
	RB-InformationReconfigList-r7,
	RB-InformationReconfigList-r8,
	RB-InformationReconfigList-r11,
	RB-InformationReleaseList,
	RB-PDCPContextRelocationList,
	SRB-InformationSetupList,
	SRB-InformationSetupList-r5,
	SRB-InformationSetupList-r6,
	SRB-InformationSetupList-r7,
	SRB-InformationSetupList-r8,
	SRB-InformationSetupList-r11,
	SRB-InformationSetupList2,
	SRB-InformationSetupList2-r6,
	SRB-InformationSetupList2-r7,
	SRB-InformationSetupList2-r8,
	UL-AMR-Rate,
	UL-CounterSynchronisationInfo,
-- Transport Channel IEs:
	CPCH-SetID,
	DL-AddReconfTransChInfo2List,
	DL-AddReconfTransChInfoList,
	DL-AddReconfTransChInfoList-r4,
	DL-AddReconfTransChInfoList-r5,
	DL-AddReconfTransChInfoList-r7,
	DL-AddReconfTransChInfoList-r9,
	DL-AddReconfTransChInfoList-TDD128-v9c0ext,
	DL-AddReconfTransChInfoList-r11,
	DL-CommonTransChInfo,
	DL-CommonTransChInfo-r4,
	DL-DeletedTransChInfoList,
	DL-DeletedTransChInfoList-r5,
	DL-DeletedTransChInfoList-r7,
	DRAC-StaticInformationList,
	HARQ-Info-r7,
	HARQ-Info-r11,
	PowerOffsetInfoShort,
	TFC-Subset,
	TFCS-Identity,
	UL-AddReconfTransChInfoList,
	UL-AddReconfTransChInfoList-r6,
	UL-AddReconfTransChInfoList-r7,
	UL-AddReconfTransChInfoList-r8,
	UL-CommonTransChInfo,
	UL-CommonTransChInfo-r4,
	UL-DeletedTransChInfoList,
	UL-DeletedTransChInfoList-r6,
-- Physical Channel IEs :
	AdditionalDLSecCellInfoListFDD,
	AdditionalDLSecCellInfoListFDD-r11,
	AdditionalDLSecCellInfoListFDD2,
	Alpha,
	BEACON-PL-Est,
	CCTrCH-PowerControlInfo,
	CCTrCH-PowerControlInfo-r4,
	CCTrCH-PowerControlInfo-r5,
	CCTrCH-PowerControlInfo-r7,
	CommonERGCHInfoFDD,
	ConstantValue,
	ConstantValueTdd,
	ControlChannelDRXInfo-TDD128-r8,
	CPCH-SetInfo,
	DHS-Sync,
	DL-CommonInformation,
	DL-CommonInformation-r4,
	DL-CommonInformation-r5,
	DL-CommonInformation-r6,
	DL-CommonInformation-r7,
	DL-CommonInformation-r8,
	DL-CommonInformation-r10,
	DL-CommonInformation-r11,
	DL-CommonInformationPost,
	DL-HSPDSCH-Information,
	DL-HSPDSCH-Information-r6,
	DL-HSPDSCH-Information-r7,
	DL-HSPDSCH-Information-r8,
	DL-HSPDSCH-Information-r8-ext,
	DL-HSPDSCH-Information-r9,
	DL-HSPDSCH-Information-r8-ext2,
	DL-HSPDSCH-Information-r11,
	DL-HSPDSCH-MultiCarrier-Information,
	DL-InformationPerRL-List,
	DL-InformationPerRL-List-r4,
	DL-InformationPerRL-List-r5,
	DL-InformationPerRL-List-r5bis,
	DL-InformationPerRL-List-r6, 
	DL-InformationPerRL-List-r7,
	DL-InformationPerRL-List-r8,
	DL-InformationPerRL-List-v6b0ext,
	DL-InformationPerRL-List-r11,
	DL-InformationPerRL-ListPostFDD,
	DL-InformationPerRL-PostTDD,
	DL-InformationPerRL-PostTDD-LCR-r4,
	DL-MultiCarrier-Information,
	DL-PDSCH-Information,
	DL-SecondaryCellInfoFDD,
	DL-SecondaryCellInfoFDD-v890ext,
	DL-SecondaryCellInfoFDD-r9,
	DL-SecondaryCellInfoFDD-r10,
	DL-SecondaryCellInfoFDD-r11,
	DL-TPC-PowerOffsetPerRL-List,
	DLUL-HSPA-Information-r8,
	DLUL-HSPA-Information-r9,
	DLUL-HSPA-Information-r10,
	DPC-Mode,
	DPCH-CompressedModeStatusInfo,
	DPCH-CompressedModeStatusInfo-r10,
	DTX-DRX-TimingInfo-r7,
	DTX-DRX-Info-r7,
	DynamicPersistenceLevel,
	E-DCH-ReconfigurationInfo,
	E-DCH-ReconfigurationInfo-SecULFrequency,
	E-DCH-ReconfigurationInfo-r7,
	E-DCH-ReconfigurationInfo-r11,
	E-DCH-RL-InfoSameServingCell,
	E-TFC-Boost-Info-r7,
	E-DPDCH-PowerInterpolation,
	EUTRA-TargetFreqInfoList-vb50ext,
	EXT-UL-TimingAdvance,
	Feedback-cycle-r7,
	FrequencyInfo,
	FrequencyInfoFDD,
	FrequencyInfoTDD,
	F-TPICH-ReconfigurationInfo,
	HARQ-Preamble-Mode,
	HS-DSCH-TBSizeTable,
	HS-SCCH-LessInfo-r7,
	HS-SICH-Power-Control-Info-TDD384,
	HS-SICH-Power-Control-Info-TDD768,
	MaxAllowedUL-TX-Power,
	MIMO-Parameters-r7,
	MIMO-Parameters-v7f0ext,
	MIMO-Parameters-v7g0ext,
	MIMO-Parameters-r8,
	MIMO-Parameters-r9,
	MIMO4x4-Parameters,
	Multi-frequencyInfo-LCR-r7,
	MU-MIMO-Info-TDD128,
	OpenLoopPowerControl-IPDL-TDD-r4,
	PDSCH-CapacityAllocationInfo,
	PDSCH-CapacityAllocationInfo-r4,
	PDSCH-CapacityAllocationInfo-r7,
	PDSCH-Identity,
	PrimaryCPICH-Info,
	PrimaryCCPCH-TX-Power,
	PUSCH-CapacityAllocationInfo,
	PUSCH-CapacityAllocationInfo-r4, 
	PUSCH-CapacityAllocationInfo-r7,
	PUSCH-Identity,
	PUSCH-SysInfoList-HCR-r5,
	PDSCH-SysInfoList-HCR-r5,
	RL-AdditionInformationList,
	RL-AdditionInformationList-r6,
	RL-AdditionInformation-list-v6b0ext,
	RL-AdditionInformationList-r7,
	RL-AdditionInformationList-r8,
	RL-AdditionInformationList-v890ext,
	RL-AdditionInformationList-r9,
	RL-AdditionInformationList-v950ext,
	RL-AdditionInformationList-r10,
	RL-AdditionInformationList-vb50ext,
	RL-AdditionInformationList-r11,
	RL-AdditionInformationList-SecULFreq,
	RL-RemovalInformationList,
	RL-RemovalInformationList-SecULFreq,
	SecondaryCellMIMOparametersFDD-v950ext,
	Serving-HSDSCH-CellInformation,
	Serving-HSDSCH-CellInformation-r7,
	Serving-HSDSCH-CellInformation-r8,
	Serving-HSDSCH-CellInformation-r9,
	Serving-HSDSCH-CellInformation-r11,
	ServingCellChangeParameters,
	SpecialBurstScheduling,
	SPS-Information-TDD128-r8,
	SSDT-Information,
	SSDT-Information-r4,
	SSDT-UL,
	StandaloneMidambleInfo-TDD128,
	TFC-ControlDuration,
	TimeslotList,
	TimeslotList-r4,
	TimingMaintainedSynchInd,
	TX-DiversityMode,
	UL-16QAM-Config,
	UL-64QAM-Config,
	UL-ChannelRequirement,
	UL-ChannelRequirement-r4,
	UL-ChannelRequirement-r5,
	UL-ChannelRequirementWithCPCH-SetID,
	UL-ChannelRequirementWithCPCH-SetID-r4,
	UL-ChannelRequirementWithCPCH-SetID-r5,
	UL-CLTD-InfoFDD,
	UL-MIMO-InfoFDD,
	UL-DPCH-Info,
	UL-DPCH-Info-r4, 
	UL-DPCH-Info-r5,
	UL-DPCH-Info-r6,
	UL-DPCH-Info-r7,
	UL-DPCH-Info-r11,
	UL-DPCH-InfoPostFDD,
	UL-DPCH-InfoPostTDD,
	UL-DPCH-InfoPostTDD-LCR-r4,
	UL-EDCH-Information-ext,
	UL-EDCH-Information-r6,
	UL-EDCH-Information-r7,
	UL-EDCH-Information-r8,
	UL-EDCH-Information-r9,
	UL-EDCH-Information-r11,
	UL-MulticarrierEDCHInfo-TDD128,
	UL-OLTD-InfoFDD,
	UL-SecondaryCellInfoFDD,
	UL-SynchronisationParameters-r4,
	UL-TimingAdvance,
	UL-TimingAdvanceControl,
	UL-TimingAdvanceControl-r4,
	UL-TimingAdvanceControl-r7,
	UpPCHposition-LCR,
-- Measurement IEs :
	AdditionalMeasurementID-List,
	AdditionalMeasurementID-List-r9,
	CellDCHMeasOccasionInfo-TDD128-r9,
	CSGProximityIndication,
	CSGProximityIndication-vb50ext,
	DeltaRSCP,
	Frequency-Band,
	EventResults,
	EventResults-v770ext,
	EventResults-v860ext,
	EventResults-va40ext,
	EventResultsOnSecUlFreq,
	EUTRA-EventResults,
	EUTRA-EventResults-vb50ext,
	EUTRA-MeasuredResults,
	EUTRA-MeasuredResults-v920ext,
	EUTRA-MeasuredResults-vb50ext,
	EUTRA-EventResultsForCELLFACH,
	Inter-FreqEventCriteriaList-v590ext,
	Intra-FreqEventCriteriaList-v590ext,
	IntraFreqReportingCriteria-1b-r5,
	IntraFreqEvent-1d-r5,
	IntraFreqCellID,
	InterFreqEventResults-LCR-r4-ext,
	InterRATCellInfoIndication,
	InterRATMeasurement-r11,
	InterRAT-TargetCellDescription,
	MeasuredResults,
	MeasuredResults-v390ext,
	MeasuredResults-v590ext,
	MeasuredResults-v770ext,
	MeasuredResults-v860ext,
	MeasuredResults-v920ext,
	MeasuredResultsOnSecUlFreq,
	MeasuredResultsListOnSecUlFreq,
	MeasuredResultsList,
	MeasuredResultsList-LCR-r4-ext,
	MeasuredResultsList-v770xet,
	MeasuredResultsList-v860ext,
	MeasuredResultsList-v920ext,
	MeasuredResultsOnRACH,
	MeasuredResultsOnRACHFDD-r11,
	MeasuredResultsOnRACH-v7g0ext,
	MeasuredResultsOnRACHinterFreq,
	MeasuredResultsOnRACH-EUTRAFreq,
	MeasurementCommand,
	MeasurementCommand-r4,
	MeasurementCommand-r6,
	MeasurementCommand-r7,
	MeasurementCommand-r8,
	MeasurementCommand-r9,
	MeasurementCommand-r10,
	MeasurementCommand-r11,
	MeasurementIdentity,
	MeasurementIdentity-r9,
	MeasurementIdentityExt,
	MeasurementReportingMode,
	NewInterFreqCellList-v7b0ext,
	NewInterFreqCellList-LCR-v8a0ext,
	NewIntraFreqCellList-LCR-v8a0ext,
	PeriodicalWithReportingCellStatusOnSecULFreq,
	PrimaryCCPCH-RSCP,
	SFN-Offset-Validity,
	TimeslotListWithISCP,
	TrafficVolumeMeasuredResultsList,
	UE-Positioning-GPS-AssistanceData,
	UE-Positioning-GPS-AssistanceData-v770ext,
	UE-Positioning-GPS-AssistanceData-v920ext,
	UE-Positioning-GPS-AssistanceData-va40ext,
	UE-Positioning-GPS-ReferenceTimeUncertainty,
	UE-Positioning-Measurement-v390ext,
	UE-Positioning-OTDOA-AssistanceData,
	UE-Positioning-OTDOA-AssistanceData-r4ext,
	UE-Positioning-OTDOA-AssistanceData-UEB,
	UE-Positioning-OTDOA-AssistanceData-UEB-ext,
	UE-Positioning-OTDOA-MeasuredResultsTDD-ext,
	UE-Positioning-GANSS-AssistanceData,
	UE-Positioning-GANSS-AssistanceData-v860ext,
	UE-Positioning-GANSS-AssistanceData-v920ext,
	UE-Positioning-GANSS-AssistanceData-va40ext,
-- Other IEs :
	BCCH-ModificationInfo,
	CDMA2000-MessageList,
	ETWS-Information,
	ETWS-WarningSecurityInfo,
	GSM-TargetCellInfoList,
	GERANIu-MessageList,
	GERAN-SystemInformation,
	GSM-MessageList,
	InterRAT-ChangeFailureCause,
	InterRAT-HO-FailureCause,
	InterRAT-UE-RadioAccessCapabilityList,
	InterRAT-UE-RadioAccessCapability-v590ext,
	InterRAT-UE-SecurityCapList,
	IntraDomainNasNodeSelector,
	MasterInformationBlock,
	MIB-ValueTag,
	ProtocolErrorMoreInformation,
	Rplmn-Information,
	Rplmn-Information-r4,
	SegCount,
	SegmentIndex,
	SFN-Prime,
	SIB-Data-fixed,
	SIB-Data-variable,
	SIB-Type,
	SysInfoType1,
	SysInfoType3,
	SysInfoType5,
	SysInfoType7,
	SysInfoType11,
	SysInfoType11bis,
	SysInfoType12,
	SysInfoTypeSB1,
	SysInfoTypeSB2,
	SysInfoType22,
-- MBMS IEs:
	MBMS-CellGroupIdentity-r6,
	MBMS-CommonRBInformationList-r6,
	MBMS-CurrentCell-SCCPCHList-r6,
	MBMS-JoinedInformation-r6,
	MBMS-MICHConfigurationInfo-r6,
	MBMS-MICHConfigurationInfo-v770ext,
	MBMS-MICHConfigurationInfo-v890ext,
	MBMS-ModifedServiceList-r6,
	MBMS-ModifiedServiceList-LCR-v7c0ext,
	MBMS-ModifiedServiceList-v770ext,
	MBMS-MSCH-ConfigurationInfo-r6,
	MBMS-NeighbouringCellSCCPCHList-r6,
	MBMS-NeighbouringCellSCCPCHList-v770ext,
	MBMS-NumberOfNeighbourCells-r6,
	MBMS-PhyChInformationList-r6,
	MBMS-PhyChInformationList-r7,
	MBMS-PhyChInformationList-IMB384,
	MBMS-PL-ServiceRestrictInfo-r6,
	MBMS-PreferredFrequencyList-r6,
	MBMS-PTMActivationTime-r6,
	MBMS-SelectedServiceInfo,
	MBMS-SelectedServicesShort,
	MBMS-ServiceAccessInfoList-r6,
	MBMS-ServiceIdentity-r6,
	MBMS-ServiceSchedulingInfoList-r6,
	MBMS-SIBType5-SCCPCHList-r6,
	MBMS-TimersAndCounters-r6,
	MBMS-TranspChInfoForEachCCTrCh-r6,
	MBMS-TranspChInfoForEachTrCh-r6,
	MBMS-UnmodifiedServiceList-r6,
	MBMS-UnmodifiedServiceList-v770ext,
	MBSFN-ClusterFrequency-r7,
	MBSFN-InterFrequencyNeighbourList-r7,
	MBSFN-InterFrequencyNeighbourList-v860ext,
	MBMS-NetworkStandardTimeInformation-LCR-v890ext,
	MBSFN-TDDInformation-LCR,
	MBSFN-TDM-Info-List,
-- MDT IEs
	LoggedMeasurementsConfigurationInfo,
	LoggedMeasurementsConfigurationInfo-r11,
	LoggedMeasReport,
	LoggedMeasReport-vb50ext,
	ConnectionEstablishmentFailureReport,
-- UTRAN ANR IEs
	LoggedANRConfigurationInfo,
	LoggedANRReportInfoList,
	LoggedANRReportInfoList-vb50ext

FROM InformationElements

	maxSIBperMsg,
	maxURNTI-Group
FROM Constant-definitions;

-- ***************************************************
--
-- ACTIVE SET UPDATE (FDD only)
--
-- ***************************************************

ActiveSetUpdate ::= CHOICE {
	r3								SEQUENCE {
		activeSetUpdate-r3				ActiveSetUpdate-r3-IEs,
		laterNonCriticalExtensions		SEQUENCE {
			-- Container for additional R99 extensions
			activeSetUpdate-r3-add-ext		BIT STRING		OPTIONAL,
			v4b0NonCriticalExtensions		SEQUENCE {
				activeSetUpdate-v4b0ext		ActiveSetUpdate-v4b0ext-IEs,
				v590NonCriticalExtensions		SEQUENCE {
					activeSetUpdate-v590ext			ActiveSetUpdate-v590ext-IEs,
					v690NonCriticalExtensions		SEQUENCE {
						activeSetUpdate-v690ext			ActiveSetUpdate-v690ext-IEs,
						nonCriticalExtensions			SEQUENCE {} OPTIONAL
					}	OPTIONAL
				}	OPTIONAL
			} OPTIONAL
		} OPTIONAL
	},
	later-than-r3					SEQUENCE {
		rrc-TransactionIdentifier		RRC-TransactionIdentifier,
		criticalExtensions				CHOICE {
			r6								SEQUENCE {
				activeSetUpdate-r6				ActiveSetUpdate-r6-IEs,
				activeSetUpdate-r6-add-ext		BIT STRING		OPTIONAL,
				v6b0NonCriticalExtensions		SEQUENCE {
					activeSetUpdate-v6b0ext			ActiveSetUpdate-v6b0ext-IEs,
					nonCriticalExtensions			SEQUENCE {}		OPTIONAL
				}	OPTIONAL
			},
			criticalExtensions				CHOICE {
				r7								SEQUENCE {
					activeSetUpdate-r7				ActiveSetUpdate-r7-IEs,
					activeSetUpdate-r7-add-ext		BIT STRING		OPTIONAL,
					v780NonCriticalExtensions		SEQUENCE {
						activeSetUpdate-v780ext			ActiveSetUpdate-v780ext-IEs,
						v7f0NonCriticalExtensions	SEQUENCE {
							activeSetUdpate-v7f0ext		ActiveSetUpdate-v7f0ext-IEs,
							v7g0NonCriticalExtensions	SEQUENCE {
								activeSetUdpate-v7g0ext		ActiveSetUpdate-v7g0ext-IEs,
								nonCriticalExtensions			SEQUENCE {}		OPTIONAL
							}	OPTIONAL
						}	OPTIONAL
					}	OPTIONAL
				},
				criticalExtensions				CHOICE {
					r8								SEQUENCE {
						activeSetUpdate-r8				ActiveSetUpdate-r8-IEs,
						-- Container for adding non critical extensions after freezing REL-9
						activeSetUpdate-r8-add-ext		BIT STRING		OPTIONAL,
						v890NonCriticalExtensions		SEQUENCE {
							activeSetUpdate-v890ext			ActiveSetUpdate-v890ext-IEs,
							v7g0NonCriticalExtensions		SEQUENCE {
								activeSetUpdate-v7g0ext			ActiveSetUpdate-v7g0ext-IEs,
								nonCriticalExtensions			SEQUENCE {}		OPTIONAL
							}	OPTIONAL
						}	OPTIONAL
					},
					criticalExtensions				CHOICE {
						r9								SEQUENCE {
							activeSetUpdate-r9				ActiveSetUpdate-r9-IEs,
							-- Container for adding non critical extensions after freezing REL-10
							activeSetUpdate-r9-add-ext		BIT STRING		OPTIONAL,
							v950NonCriticalExtensions		SEQUENCE {
								activeSetUpdate-v950ext			ActiveSetUpdate-v950ext-IEs,
								nonCriticalExtensions			SEQUENCE {}		OPTIONAL
							}	OPTIONAL
						},
						criticalExtensions				CHOICE {
							r10								SEQUENCE {
								activeSetUpdate-r10				ActiveSetUpdate-r10-IEs,
								-- Container for adding non critical extensions after freezing 
								-- REL-11
								activeSetUpdate-r10-add-ext		BIT STRING		OPTIONAL,
								vb50NonCriticalExtensions		SEQUENCE {
									activeSetUpdate-vb50ext			ActiveSetUpdate-vb50ext-IEs,
									nonCriticalExtensions			SEQUENCE {}		OPTIONAL
								}	OPTIONAL
							},
							criticalExtensions				CHOICE {
								r11								SEQUENCE {
									activeSetUpdate-r11				ActiveSetUpdate-r11-IEs,
									-- Container for adding non critical extensions after freezing 
									-- REL-12
									activeSetUpdate-r11-add-ext		BIT STRING		OPTIONAL,
									nonCriticalExtensions			SEQUENCE {}		OPTIONAL
								},
								criticalExtensions				SEQUENCE {}
							}
						}
					}
				}
			}
		}
	}
}

ActiveSetUpdate-r3-IEs ::= SEQUENCE {
	-- User equipment IEs
		rrc-TransactionIdentifier		RRC-TransactionIdentifier,
		-- dummy and dummy2 are not used in this version of the specification, they should
		-- not be sent and if received they should be ignored.
		dummy						IntegrityProtectionModeInfo			OPTIONAL,
		dummy2						CipheringModeInfo					OPTIONAL,
		activationTime					ActivationTime						OPTIONAL,
		newU-RNTI						U-RNTI								OPTIONAL,
	-- Core network IEs
		cn-InformationInfo				CN-InformationInfo					OPTIONAL,
	-- Radio bearer IEs
		-- dummy3 is not used in this version of the specification, it should
		-- not be sent and if received it should be ignored.
		dummy3						DL-CounterSynchronisationInfo		OPTIONAL,
	-- Physical channel IEs
		maxAllowedUL-TX-Power			MaxAllowedUL-TX-Power				OPTIONAL,
		rl-AdditionInformationList		RL-AdditionInformationList			OPTIONAL,
		rl-RemovalInformationList		RL-RemovalInformationList			OPTIONAL,
		tx-DiversityMode				TX-DiversityMode					OPTIONAL,
		-- dummy4 is not used in this version of the specification, it should
		-- not be sent and if received it should be ignored.
		dummy4							SSDT-Information					OPTIONAL
}

ActiveSetUpdate-v4b0ext-IEs ::= SEQUENCE {
	-- Physical channel IEs
		-- dummy is not used in this version of the specification, it should
		-- not be sent and if received it should be ignored.
		dummy								SSDT-UL								OPTIONAL,
		-- The order of the RLs in IE cell-id-PerRL-List is the same as
		-- in IE RL-AdditionInformationList included in this message
		cell-id-PerRL-List					CellIdentity-PerRL-List				OPTIONAL
}

ActiveSetUpdate-v590ext-IEs ::= SEQUENCE {
	-- Physical channel IEs
		dpc-Mode							DPC-Mode,
		dl-TPC-PowerOffsetPerRL-List		DL-TPC-PowerOffsetPerRL-List			OPTIONAL
}

ActiveSetUpdate-v690ext-IEs ::= SEQUENCE {
	-- Core network IEs
		primary-plmn-Identity				PLMN-Identity						OPTIONAL
}

ActiveSetUpdate-r6-IEs ::= SEQUENCE {
	-- User equipment IEs
		activationTime						ActivationTime						OPTIONAL,
		newU-RNTI							U-RNTI								OPTIONAL,
		newH-RNTI							H-RNTI								OPTIONAL,
		newPrimary-E-RNTI					E-RNTI								OPTIONAL,
		newSecondary-E-RNTI					E-RNTI								OPTIONAL,
	-- Core network IEs
		cn-InformationInfo					CN-InformationInfo-r6				OPTIONAL,
	-- Physical channel IEs
		maxAllowedUL-TX-Power				MaxAllowedUL-TX-Power				OPTIONAL,
		rl-AdditionInformationList			RL-AdditionInformationList-r6		OPTIONAL,
		rl-RemovalInformationList			RL-RemovalInformationList			OPTIONAL,
		tx-DiversityMode					TX-DiversityMode					OPTIONAL,
		dpc-Mode							DPC-Mode							OPTIONAL,
		serving-HSDSCH-CellInformation		Serving-HSDSCH-CellInformation		OPTIONAL,
		e-dch-ReconfigurationInfo			E-DCH-ReconfigurationInfo			OPTIONAL
}

ActiveSetUpdate-v6b0ext-IEs ::= SEQUENCE {
	-- Physical channel IEs
		rl-AdditionInformation-list-v6b0ext		RL-AdditionInformation-list-v6b0ext	OPTIONAL
}

ActiveSetUpdate-r7-IEs ::= SEQUENCE {
	-- User equipment IEs
		activationTime						ActivationTime						OPTIONAL,
		newU-RNTI							U-RNTI								OPTIONAL,
		newH-RNTI							H-RNTI								OPTIONAL,
		newPrimary-E-RNTI					E-RNTI								OPTIONAL,
		newSecondary-E-RNTI					E-RNTI								OPTIONAL,
	-- Core network IEs
		cn-InformationInfo					CN-InformationInfo-r6				OPTIONAL,
	-- Physical channel IEs
		dtx-drx-TimingInfo					DTX-DRX-TimingInfo-r7				OPTIONAL,
		dtx-drx-Info						DTX-DRX-Info-r7						OPTIONAL,
		hs-scch-LessInfo					HS-SCCH-LessInfo-r7					OPTIONAL,
		mimoParameters						MIMO-Parameters-r7					OPTIONAL,
		maxAllowedUL-TX-Power				MaxAllowedUL-TX-Power				OPTIONAL,
		rl-AdditionInformationList			RL-AdditionInformationList-r7		OPTIONAL,
		rl-RemovalInformationList			RL-RemovalInformationList			OPTIONAL,
		tx-DiversityMode					TX-DiversityMode					OPTIONAL,
		dpc-Mode							DPC-Mode							OPTIONAL,
		serving-HSDSCH-CellInformation		Serving-HSDSCH-CellInformation-r7	OPTIONAL,
		e-dch-ReconfigurationInfo			E-DCH-ReconfigurationInfo-r7		OPTIONAL,
		ul-16QAM-Config						UL-16QAM-Config						OPTIONAL,
		e-dch-ReconfInfoSameCell			E-DCH-RL-InfoSameServingCell		OPTIONAL,
		e-TFC-Boost-Info					E-TFC-Boost-Info-r7					OPTIONAL,
		e-DPDCH-PowerInterpolation			E-DPDCH-PowerInterpolation			OPTIONAL
}

ActiveSetUpdate-v780ext-IEs ::= SEQUENCE {
	-- Physical channel IEs
		hs-DSCH-TBSizeTable					HS-DSCH-TBSizeTable					OPTIONAL
}

ActiveSetUpdate-v7f0ext-IEs ::= SEQUENCE {
	-- Physical channel IEs
	mimoParameters							MIMO-Parameters-v7f0ext				OPTIONAL
}

ActiveSetUpdate-v7g0ext-IEs ::= SEQUENCE {
	-- Physical channel IEs
	mimoParameters							MIMO-Parameters-v7g0ext				OPTIONAL
}

ActiveSetUpdate-r8-IEs ::= SEQUENCE {
	-- User equipment IEs
		activationTime						ActivationTime						OPTIONAL,
		newU-RNTI							U-RNTI								OPTIONAL,
		newH-RNTI							H-RNTI								OPTIONAL,
		newPrimary-E-RNTI					E-RNTI								OPTIONAL,
		newSecondary-E-RNTI					E-RNTI								OPTIONAL,
	-- Core network IEs
		cn-InformationInfo					CN-InformationInfo-r6				OPTIONAL,
	-- Physical channel IEs
		dtx-drx-TimingInfo					DTX-DRX-TimingInfo-r7				OPTIONAL,
		dtx-drx-Info						DTX-DRX-Info-r7						OPTIONAL,
		hs-scch-LessInfo					HS-SCCH-LessInfo-r7					OPTIONAL,
		mimoParameters						MIMO-Parameters-r8					OPTIONAL,
		maxAllowedUL-TX-Power				MaxAllowedUL-TX-Power				OPTIONAL,
		rl-AdditionInformationList			RL-AdditionInformationList-r8		OPTIONAL,
		servingCellChangeParameters			ServingCellChangeParameters			OPTIONAL,
		rl-RemovalInformationList			RL-RemovalInformationList			OPTIONAL,
		tx-DiversityMode					TX-DiversityMode					OPTIONAL,
		dpc-Mode							DPC-Mode							OPTIONAL,
		serving-HSDSCH-CellInformation		Serving-HSDSCH-CellInformation-r8	OPTIONAL,
		e-dch-ReconfigurationInfo			E-DCH-ReconfigurationInfo-r7		OPTIONAL,
		ul-16QAM-Config						UL-16QAM-Config						OPTIONAL,
		e-dch-ReconfInfoSameCell			E-DCH-RL-InfoSameServingCell		OPTIONAL,
		e-TFC-Boost-Info					E-TFC-Boost-Info-r7					OPTIONAL,
		e-DPDCH-PowerInterpolation			E-DPDCH-PowerInterpolation			OPTIONAL,
		dl-SecondaryCellInfoFDD				DL-SecondaryCellInfoFDD				OPTIONAL
}

ActiveSetUpdate-v890ext-IEs ::= SEQUENCE {
	-- Physical channel IEs
		dl-SecondaryCellInfoFDD-v890ext		DL-SecondaryCellInfoFDD-v890ext		OPTIONAL,
		mimoParameters						MIMO-Parameters-v7f0ext				OPTIONAL,
		rl-AdditionInformationList			RL-AdditionInformationList-v890ext	OPTIONAL
}

ActiveSetUpdate-r9-IEs ::= SEQUENCE {
	-- User equipment IEs
		activationTime						ActivationTime						OPTIONAL,
		newU-RNTI							U-RNTI								OPTIONAL,
		newH-RNTI							H-RNTI								OPTIONAL,
		newPrimary-E-RNTI					E-RNTI								OPTIONAL,
		newSecondary-E-RNTI					E-RNTI								OPTIONAL,
	-- Core network IEs
		cn-InformationInfo					CN-InformationInfo-r6				OPTIONAL,
	-- Physical channel IEs
		dtx-drx-TimingInfo					DTX-DRX-TimingInfo-r7				OPTIONAL,
		dtx-drx-Info						DTX-DRX-Info-r7						OPTIONAL,
		hs-scch-LessInfo					HS-SCCH-LessInfo-r7					OPTIONAL,
		mimoParameters						MIMO-Parameters-r9					OPTIONAL,
		maxAllowedUL-TX-Power				MaxAllowedUL-TX-Power				OPTIONAL,
		ul-SecondaryCellInfoFDD				UL-SecondaryCellInfoFDD				OPTIONAL,
		e-dch-ReconfigurationInfo-SecULFrequency	
									E-DCH-ReconfigurationInfo-SecULFrequency	OPTIONAL,
		rl-AdditionInformationList			RL-AdditionInformationList-r9		OPTIONAL,
		rl-AdditionInformationList-SecULFreq 
									RL-AdditionInformationList-SecULFreq		OPTIONAL,
		servingCellChangeParameters			ServingCellChangeParameters			OPTIONAL,
		rl-RemovalInformationList			RL-RemovalInformationList			OPTIONAL,
		rl-RemovalInformationList-SecULFreq 
									RL-RemovalInformationList-SecULFreq			OPTIONAL,
		tx-DiversityMode					TX-DiversityMode					OPTIONAL,
		dpc-Mode							DPC-Mode							OPTIONAL,
		serving-HSDSCH-CellInformation		Serving-HSDSCH-CellInformation-r9	OPTIONAL,
		e-dch-ReconfigurationInfo			E-DCH-ReconfigurationInfo-r7		OPTIONAL,
		ul-16QAM-Config						UL-16QAM-Config						OPTIONAL,
		e-dch-ReconfInfoSameCell			E-DCH-RL-InfoSameServingCell		OPTIONAL,
		e-TFC-Boost-Info					E-TFC-Boost-Info-r7					OPTIONAL,
		e-DPDCH-PowerInterpolation			E-DPDCH-PowerInterpolation			OPTIONAL,
		dl-SecondaryCellInfoFDD				DL-SecondaryCellInfoFDD-r9			OPTIONAL
}

ActiveSetUpdate-v950ext-IEs ::= SEQUENCE {
	-- Physical channel IEs
		secondaryCellMimoParameters			SecondaryCellMIMOparametersFDD-v950ext		OPTIONAL,
		rl-AdditionInformationList			RL-AdditionInformationList-v950ext			OPTIONAL
}

ActiveSetUpdate-r10-IEs ::= SEQUENCE {
	-- User equipment IEs
		activationTime						ActivationTime						OPTIONAL,
		newU-RNTI							U-RNTI								OPTIONAL,
		newH-RNTI							H-RNTI								OPTIONAL,
		newPrimary-E-RNTI					E-RNTI								OPTIONAL,
		newSecondary-E-RNTI					E-RNTI								OPTIONAL,
	-- Core network IEs
		cn-InformationInfo					CN-InformationInfo-r6				OPTIONAL,
	-- Physical channel IEs
		dtx-drx-TimingInfo					DTX-DRX-TimingInfo-r7				OPTIONAL,
		dtx-drx-Info						DTX-DRX-Info-r7						OPTIONAL,
		hs-scch-LessInfo					HS-SCCH-LessInfo-r7					OPTIONAL,
		mimoParameters						MIMO-Parameters-r9					OPTIONAL,
		maxAllowedUL-TX-Power				MaxAllowedUL-TX-Power				OPTIONAL,
		ul-SecondaryCellInfoFDD				UL-SecondaryCellInfoFDD				OPTIONAL,
		e-dch-ReconfigurationInfo-SecULFrequency	
									E-DCH-ReconfigurationInfo-SecULFrequency	OPTIONAL,
		rl-AdditionInformationList			RL-AdditionInformationList-r10		OPTIONAL,
		rl-AdditionInformationList-SecULFreq 
									RL-AdditionInformationList-SecULFreq		OPTIONAL,
		servingCellChangeParameters			ServingCellChangeParameters			OPTIONAL,
		rl-RemovalInformationList			RL-RemovalInformationList			OPTIONAL,
		rl-RemovalInformationList-SecULFreq 
									RL-RemovalInformationList-SecULFreq			OPTIONAL,
		tx-DiversityMode					TX-DiversityMode					OPTIONAL,
		dpc-Mode							DPC-Mode							OPTIONAL,
		serving-HSDSCH-CellInformation		Serving-HSDSCH-CellInformation-r9	OPTIONAL,
		e-dch-ReconfigurationInfo			E-DCH-ReconfigurationInfo-r7		OPTIONAL,
		ul-16QAM-Config						UL-16QAM-Config						OPTIONAL,
		e-dch-ReconfInfoSameCell			E-DCH-RL-InfoSameServingCell		OPTIONAL,
		e-TFC-Boost-Info					E-TFC-Boost-Info-r7					OPTIONAL,
		e-DPDCH-PowerInterpolation			E-DPDCH-PowerInterpolation			OPTIONAL,
		dl-SecondaryCellInfoFDD				DL-SecondaryCellInfoFDD-r10			OPTIONAL,
		additionalDLSecCellInfoListFDD		AdditionalDLSecCellInfoListFDD		OPTIONAL
}

ActiveSetUpdate-vb50ext-IEs ::= SEQUENCE {
		ulOLTDInfoFDD						UL-OLTD-InfoFDD			OPTIONAL,
		rl-AdditionInformationList			RL-AdditionInformationList-vb50ext		
																				OPTIONAL
}

ActiveSetUpdate-r11-IEs ::= SEQUENCE {
	-- User equipment IEs
		activationTime						ActivationTime						OPTIONAL,
		newU-RNTI							U-RNTI								OPTIONAL,
		newH-RNTI							H-RNTI								OPTIONAL,
		newPrimary-E-RNTI					E-RNTI								OPTIONAL,
		newSecondary-E-RNTI					E-RNTI								OPTIONAL,
	-- Core network IEs
		cn-InformationInfo					CN-InformationInfo-r6				OPTIONAL,
	-- Physical channel IEs
		dtx-drx-TimingInfo					DTX-DRX-TimingInfo-r7				OPTIONAL,
		dtx-drx-Info						DTX-DRX-Info-r7						OPTIONAL,
		hs-scch-LessInfo					HS-SCCH-LessInfo-r7					OPTIONAL,
		mimoParameters						MIMO-Parameters-r9					OPTIONAL,
		mimo4x4Parameters					MIMO4x4-Parameters					OPTIONAL,
		maxAllowedUL-TX-Power				MaxAllowedUL-TX-Power				OPTIONAL,
		ul-SecondaryCellInfoFDD				UL-SecondaryCellInfoFDD				OPTIONAL,
		e-dch-ReconfigurationInfo-SecULFrequency	
									E-DCH-ReconfigurationInfo-SecULFrequency	OPTIONAL,
		ul-CLTD-InfoFDD						UL-CLTD-InfoFDD						OPTIONAL,
		f-tpich-ReconfigurationInfo			F-TPICH-ReconfigurationInfo			OPTIONAL,
		ul-OLTD-InfoFDD						UL-OLTD-InfoFDD						OPTIONAL,
		rl-AdditionInformationList			RL-AdditionInformationList-r11		OPTIONAL,
		rl-AdditionInformationList-SecULFreq 
									RL-AdditionInformationList-SecULFreq		OPTIONAL,
		servingCellChangeParameters			ServingCellChangeParameters			OPTIONAL,
		rl-RemovalInformationList			RL-RemovalInformationList			OPTIONAL,
		rl-RemovalInformationList-SecULFreq 
									RL-RemovalInformationList-SecULFreq			OPTIONAL,
		tx-DiversityMode					TX-DiversityMode					OPTIONAL,
		dpc-Mode							DPC-Mode							OPTIONAL,
		serving-HSDSCH-CellInformation		Serving-HSDSCH-CellInformation-r11	OPTIONAL,
		e-dch-ReconfigurationInfo			E-DCH-ReconfigurationInfo-r11		OPTIONAL,
		ul-16QAM-Config						UL-16QAM-Config						OPTIONAL,
		ul-64QAM-Config						UL-64QAM-Config						OPTIONAL,
		ul-MIMO-InfoFDD						UL-MIMO-InfoFDD						OPTIONAL,
		e-dch-ReconfInfoSameCell			E-DCH-RL-InfoSameServingCell		OPTIONAL,
		e-TFC-Boost-Info					E-TFC-Boost-Info-r7					OPTIONAL,
		e-DPDCH-PowerInterpolation			E-DPDCH-PowerInterpolation			OPTIONAL,
		dl-SecondaryCellInfoFDD				DL-SecondaryCellInfoFDD-r11		OPTIONAL,
		additionalDLSecCellInfoListFDD		AdditionalDLSecCellInfoListFDD-r11	OPTIONAL,
		additionalDLSecCellInfoListFDD2		AdditionalDLSecCellInfoListFDD2		OPTIONAL
}

-- ***************************************************
--
-- ACTIVE SET UPDATE COMPLETE (FDD only)
--
-- ***************************************************

ActiveSetUpdateComplete ::= SEQUENCE {
	-- User equipment IEs
		rrc-TransactionIdentifier		RRC-TransactionIdentifier,
		-- dummy is not used in this version of the specification, it should
		-- not be sent and if received it should be ignored.
		dummy						IntegrityProtActivationInfo			OPTIONAL,
	-- Radio bearer IEs
		-- dummy2 and dummy3 are not used in this version of the specification, they should
		-- not be sent and if received they should be ignored.
		dummy2						RB-ActivationTimeInfoList			OPTIONAL,
		dummy3						UL-CounterSynchronisationInfo		OPTIONAL,
		laterNonCriticalExtensions		SEQUENCE {
			-- Container for additional R99 extensions
			activeSetUpdateComplete-r3-add-ext		BIT STRING		OPTIONAL,
			nonCriticalExtensions			SEQUENCE {}	OPTIONAL
		}	OPTIONAL
}

-- ***************************************************
--
-- ACTIVE SET UPDATE FAILURE (FDD only)
--
-- ***************************************************

ActiveSetUpdateFailure ::= SEQUENCE {
	-- User equipment IEs
		rrc-TransactionIdentifier		RRC-TransactionIdentifier,
		failureCause					FailureCauseWithProtErr,
		laterNonCriticalExtensions		SEQUENCE {
			-- Container for additional R99 extensions
			activeSetUpdateFailure-r3-add-ext		BIT STRING		OPTIONAL,
			nonCriticalExtensions			SEQUENCE {}	OPTIONAL
	}	OPTIONAL
}

-- ***************************************************
--
-- ASSISTANCE DATA DELIVERY--
-- ***************************************************

AssistanceDataDelivery ::= CHOICE {
	r3								SEQUENCE {
		assistanceDataDelivery-r3		AssistanceDataDelivery-r3-IEs,
		v3a0NonCriticalExtensions		SEQUENCE {
			assistanceDataDelivery-v3a0ext	AssistanceDataDelivery-v3a0ext,
			laterNonCriticalExtensions		SEQUENCE {
				-- Container for additional R99 extensions
				assistanceDataDelivery-r3-add-ext		BIT STRING		OPTIONAL,
				v4b0NonCriticalExtensions		SEQUENCE { 
					assistanceDataDelivery-v4b0ext	AssistanceDataDelivery-v4b0ext-IEs,
					v770NonCriticalExtension		SEQUENCE {
						assistanceDataDelivery-v770ext	AssistanceDataDelivery-v770ext-IEs,
						v860NonCriticalExtension		SEQUENCE {
							assistanceDataDelivery-v860ext	AssistanceDataDelivery-v860ext-IEs,
							v920NonCriticalExtension			SEQUENCE {
								assistanceDataDelivery-v920ext	AssistanceDataDelivery-v920ext-IEs,
								va40NonCriticalExtension		SEQUENCE {
									assistanceDataDelivery-va40ext	
																AssistanceDataDelivery-va40ext-IEs,
									nonCriticalExtensions			SEQUENCE {}		OPTIONAL
								}	OPTIONAL
							}	OPTIONAL
						}	OPTIONAL
					}	OPTIONAL
				}	OPTIONAL
			}	OPTIONAL
		}	OPTIONAL
	},
	later-than-r3					SEQUENCE {
		rrc-TransactionIdentifier		RRC-TransactionIdentifier,
		criticalExtensions				SEQUENCE {}
	}
}

AssistanceDataDelivery-r3-IEs ::=		SEQUENCE {
	-- User equipment IEs
	rrc-TransactionIdentifier				RRC-TransactionIdentifier,
	-- Measurement Information Elements
	ue-positioning-GPS-AssistanceData		UE-Positioning-GPS-AssistanceData			OPTIONAL,
	ue-positioning-OTDOA-AssistanceData-UEB	UE-Positioning-OTDOA-AssistanceData-UEB		OPTIONAL
}

AssistanceDataDelivery-v3a0ext ::= SEQUENCE {
	sfn-Offset-Validity					SFN-Offset-Validity		OPTIONAL
}

AssistanceDataDelivery-v4b0ext-IEs ::= SEQUENCE {
	ue-Positioning-OTDOA-AssistanceData-r4ext	UE-Positioning-OTDOA-AssistanceData-r4ext	OPTIONAL
}

AssistanceDataDelivery-v770ext-IEs ::= SEQUENCE {
	ue-Positioning-OTDOA-AssistanceData-UEB-ext
										UE-Positioning-OTDOA-AssistanceData-UEB-ext		OPTIONAL,
	ue-Positioning-GPS-AssistanceData	UE-Positioning-GPS-AssistanceData-v770ext		OPTIONAL,
	ue-positioning-GANSS-AssistanceData	UE-Positioning-GANSS-AssistanceData				OPTIONAL
}

AssistanceDataDelivery-v860ext-IEs ::= SEQUENCE {
	ue-positioning-GANSS-AssistanceData-v860ext
										UE-Positioning-GANSS-AssistanceData-v860ext		OPTIONAL
}

AssistanceDataDelivery-v920ext-IEs ::= SEQUENCE {
	ue-positioning-GPS-AssistanceData-v920ext 
									UE-Positioning-GPS-AssistanceData-v920ext			OPTIONAL,
	ue-positioning-GANSS-AssistanceData-v920ext
									UE-Positioning-GANSS-AssistanceData-v920ext			OPTIONAL
}

AssistanceDataDelivery-va40ext-IEs ::= SEQUENCE {
	ue-positioning-GPS-AssistanceData-va40ext 
									UE-Positioning-GPS-AssistanceData-va40ext			OPTIONAL,
	ue-positioning-GANSS-AssistanceData-va40ext
									UE-Positioning-GANSS-AssistanceData-va40ext			OPTIONAL
}

-- ***************************************************
--
-- CELL CHANGE ORDER FROM UTRAN
--
-- ***************************************************

CellChangeOrderFromUTRAN ::= CHOICE {
	r3								SEQUENCE {
		cellChangeOrderFromUTRAN-IEs		CellChangeOrderFromUTRAN-r3-IEs,
		laterNonCriticalExtensions		SEQUENCE {
			-- Container for additional R99 extensions
			cellChangeOrderFromUTRAN-r3-add-ext		BIT STRING		OPTIONAL,
			v590NonCriticalExtensions			SEQUENCE {
				cellChangeOrderFromUTRAN-v590ext	CellChangeOrderFromUTRAN-v590ext-IEs,
				nonCriticalExtensions			SEQUENCE {}	OPTIONAL
			}	OPTIONAL
		}	OPTIONAL
	},
	later-than-r3					SEQUENCE {
		rrc-TransactionIdentifier		RRC-TransactionIdentifier,
		criticalExtensions				SEQUENCE {}
	}
}

CellChangeOrderFromUTRAN-r3-IEs ::= SEQUENCE {
	-- User equipment IEs
		rrc-TransactionIdentifier		RRC-TransactionIdentifier,
		-- dummy is not used in this version of the specification, it should
		-- not be sent and if received it should be ignored.
		dummy							IntegrityProtectionModeInfo			OPTIONAL,
		activationTime					ActivationTime						OPTIONAL,
		-- the IE rab-InformationList is not used in this version of the specification, it should
		-- not be sent and if received it should be ignored. The IE may be used in a later
		-- version of the protocol and hence it is not changed into a dummy
		rab-InformationList				RAB-InformationList					OPTIONAL,
		interRAT-TargetCellDescription	InterRAT-TargetCellDescription
}

CellChangeOrderFromUTRAN-v590ext-IEs ::= SEQUENCE {		
		geran-SystemInfoType				CHOICE	{		
			sI									GERAN-SystemInformation,
			pSI									GERAN-SystemInformation
		}		OPTIONAL
}

-- ***************************************************
--
-- CELL CHANGE ORDER FROM UTRAN FAILURE
--
-- ***************************************************

CellChangeOrderFromUTRANFailure ::= CHOICE {
	r3								SEQUENCE {
		cellChangeOrderFromUTRANFailure-r3
										CellChangeOrderFromUTRANFailure-r3-IEs,
		laterNonCriticalExtensions		SEQUENCE {
			-- Container for additional R99 extensions
			cellChangeOrderFromUTRANFailure-r3-add-ext		BIT STRING	OPTIONAL,
			nonCriticalExtensions			SEQUENCE {}	OPTIONAL
		}	OPTIONAL
	},
	-- dummy is not used in this version of the specification and it
	-- should be ignored.
	dummy							SEQUENCE {
		rrc-TransactionIdentifier		RRC-TransactionIdentifier,
		criticalExtensions				SEQUENCE {}
	}
}

CellChangeOrderFromUTRANFailure-r3-IEs ::= SEQUENCE {
	-- User equipment IEs
		rrc-TransactionIdentifier		RRC-TransactionIdentifier,
		-- dummy is not used in this version of the specification, it should
		-- not be sent and if received it should be ignored.
		dummy							IntegrityProtectionModeInfo			OPTIONAL,
		interRAT-ChangeFailureCause		InterRAT-ChangeFailureCause
}

-- ***************************************************
--
-- CELL UPDATE
--
-- ***************************************************

CellUpdate ::= SEQUENCE {
	-- User equipment IEs
		u-RNTI							U-RNTI,
		startList		STARTList,
		am-RLC-ErrorIndicationRb2-3or4		BOOLEAN,
		am-RLC-ErrorIndicationRb5orAbove	BOOLEAN,
		cellUpdateCause					CellUpdateCause,
		-- TABULAR: RRC transaction identifier is nested in FailureCauseWithProtErrTrId
		failureCause					FailureCauseWithProtErrTrId			OPTIONAL,
		rb-timer-indicator				Rb-timer-indicator,
	-- Measurement IEs
		measuredResultsOnRACH			MeasuredResultsOnRACH				OPTIONAL,
		laterNonCriticalExtensions		SEQUENCE {
			-- Container for additional R99 extensions
			-- The cellUpdate-r3-add-ext can be omitted if its inclusion would result in the 
			-- size of the message exceeding the maximum PDU size possible for CCCH
			-- transmission
			cellUpdate-r3-add-ext			BIT STRING
								(CONTAINING CellUpdate-r3-add-ext-IEs)		OPTIONAL,
			v590NonCriticalExtensions	SEQUENCE {
				cellUpdate-v590ext	CellUpdate-v590ext, 
				v690NonCriticalExtensions		SEQUENCE {
					cellUpdate-v690ext				CellUpdate-v690ext-IEs,
					v6b0NonCriticalExtensions		SEQUENCE {
						cellUpdate-v6b0ext				CellUpdate-v6b0ext-IEs,
						v770NonCriticalExtensions		SEQUENCE {
							cellUpdate-v770ext				CellUpdate-v770ext-IEs,
							v860NonCriticalExtensions		SEQUENCE {
								cellUpdate-v860ext				CellUpdate-v860ext-IEs,
								-- The va40NonCriticalExtensions can be omitted if its inclusion
								-- would result in the size of the message exceeding the maximum PDU
								-- size possible for CCCH transmission
								va40NonCriticalExtensions		SEQUENCE {
									cellUpdate-va40ext				CellUpdate-va40ext-IEs,
									vb50NonCriticalExtensions		SEQUENCE {
										cellUpdate-vb50ext				CellUpdate-vb50ext-IEs,
										nonCriticalExtensions			SEQUENCE {}	OPTIONAL
									}		OPTIONAL
								}		OPTIONAL
							}		OPTIONAL
						}		OPTIONAL
					}		OPTIONAL
				}		OPTIONAL
			}		OPTIONAL
		}	OPTIONAL
}

CellUpdate-r3-add-ext-IEs ::=		SEQUENCE {
	cellUpdate-v7e0ext					CellUpdate-v7e0ext-IEs,
	v7g0NonCriticalExtensions		SEQUENCE {
		cellUpdate-v7g0ext				CellUpdate-v7g0ext-IEs,
		nonCriticalExtensions			SEQUENCE {}	OPTIONAL
	}		OPTIONAL
}

CellUpdate-v590ext ::= SEQUENCE {
	establishmentCause				EstablishmentCause	OPTIONAL
}

CellUpdate-v690ext-IEs ::=			SEQUENCE {
	-- User equipment IEs
		cellUpdateCause-ext				CellUpdateCause-ext					OPTIONAL,
		trafficVolumeIndicator			ENUMERATED { true }					OPTIONAL,
	-- Measurement IEs
		measuredResultsOnRACHinterFreq	MeasuredResultsOnRACHinterFreq		OPTIONAL,
		reconfigurationStatusIndicator	ENUMERATED { true }					OPTIONAL
}

CellUpdate-v6b0ext-IEs ::=			SEQUENCE {
	-- MBMS IEs
	-- The mbmsSelectedServices can be omitted if its inclusion would result in the 
	-- size of the message exceeding the maximum PDU size possible for CCCH transmission
		mbmsSelectedServices			MBMS-SelectedServicesShort			OPTIONAL
}

CellUpdate-v770ext-IEs ::=			SEQUENCE {
	-- User equipment IEs
		csCallType						ENUMERATED { speech, video, other, spare }	OPTIONAL,
		hspdschReception-CellFach		ENUMERATED { true }					OPTIONAL,
		ueMobilityStateIndicator		High-MobilityDetected				OPTIONAL,
		capabilityChangeIndicator		ENUMERATED { true }					OPTIONAL
}

CellUpdate-v7e0ext-IEs ::=			SEQUENCE {
	-- User equipment IEs
		supportForTwoDRXSchemesInPCH		ENUMERATED { true }				OPTIONAL
}

CellUpdate-v7g0ext-IEs ::=			SEQUENCE {
	-- Measurement IEs
		measuredResultsOnRACH-v7g0ext		MeasuredResultsOnRACH-v7g0ext		OPTIONAL
}

CellUpdate-v860ext-IEs ::=			SEQUENCE {
	-- User equipment IEs
		supportOfCommonEDCH				ENUMERATED { true }					OPTIONAL,
		supportOfHS-DSCHDRXOperation	ENUMERATED { true }					OPTIONAL,
		supportOfMACiis					ENUMERATED { true }					OPTIONAL,
		supportOfSPSOperation			ENUMERATED { true }					OPTIONAL,
		supportOfControlChannelDRXOperation
										ENUMERATED { true }					OPTIONAL
}

CellUpdate-va40ext-IEs ::= 			SEQUENCE {
	-- User equipment IEs
		securityRevertStatusIndicator	ENUMERATED { revertedBack, normalOperation }	OPTIONAL,
	-- Other IEs
		loggedMeasAvailable				ENUMERATED { true }					OPTIONAL,
		loggedANRResultsAvailable		ENUMERATED { true }					OPTIONAL
}

-- TABULAR: TDD related IEs, MBMS IEs, and supportForTwoDRXSchemesInPCH are omitted compared to 
-- tabular for the purpose of coding optimisation
CellUpdateFDD-r11	::=	SEQUENCE	{
-- User equipment IEs
	u-RNTI		U-RNTI,
	startList	STARTList,
	am-RLC-ErrorIndicationRb2-3or4				BOOLEAN,
	am-RLC-ErrorIndicationRb5orAbove			BOOLEAN,
	cellUpdateCause					CellUpdateCause,
	-- TABULAR: RRC transaction identifier is nested in FailureCauseWithProtErrTrId
	failureCause					FailureCauseWithProtErrTrId		OPTIONAL,
	rb-timer-indicator				Rb-timer-indicator,
	establishmentCause				EstablishmentCause				OPTIONAL,
	trafficVolumeIndicator			ENUMERATED { true }				OPTIONAL,
	reconfigurationStatusIndicator	ENUMERATED { true }				OPTIONAL,
	csCallType		ENUMERATED { speech, video, other, spare }		OPTIONAL,
	hspdschReception-CellFach		ENUMERATED { true }				OPTIONAL,
	ueMobilityStateIndicator		High-MobilityDetected			OPTIONAL,
	capabilityChangeIndicator		ENUMERATED { true }				OPTIONAL,
	supportOfCommonEDCH				ENUMERATED { true }				OPTIONAL,
	supportOfHS-DSCHDRXOperation	ENUMERATED { true }				OPTIONAL,
	supportOfMACiis					ENUMERATED { true }				OPTIONAL,
	securityRevertStatusIndicator	ENUMERATED { revertedBack, normalOperation }	OPTIONAL,
	spare4							ENUMERATED { true }				OPTIONAL,
	spare3							ENUMERATED { true }				OPTIONAL,
	spare2							ENUMERATED { true }				OPTIONAL,
	spare1							ENUMERATED { true }				OPTIONAL,
-- Measurement IEs
	measuredResultsOnRACH			MeasuredResultsOnRACHFDD-r11	OPTIONAL,
-- Other IEs
	loggedMeasAvailable				ENUMERATED { true }				OPTIONAL,
	loggedANRResultsAvailable		ENUMERATED { true }				OPTIONAL
}

CellUpdate-vb50ext-IEs ::= 			SEQUENCE {
	-- Measurement IEs
		measuredResultsOnRACHEUTRAFreq		MeasuredResultsOnRACH-EUTRAFreq		OPTIONAL
}

-- ***************************************************
--
-- CELL UPDATE CONFIRM
--
-- ***************************************************

CellUpdateConfirm ::= CHOICE {
	r3								SEQUENCE {
		cellUpdateConfirm-r3			CellUpdateConfirm-r3-IEs,
		v3a0NonCriticalExtensions		SEQUENCE {
			cellUpdateConfirm-v3a0ext		CellUpdateConfirm-v3a0ext,
			laterNonCriticalExtensions		SEQUENCE {
				-- Container for additional R99 extensions
				cellUpdateConfirm-r3-add-ext	BIT STRING	OPTIONAL,
				v4b0NonCriticalExtensions		SEQUENCE {
					cellUpdateConfirm-v4b0ext		CellUpdateConfirm-v4b0ext-IEs,
					v590NonCriticalExtenstions		SEQUENCE {
						cellUpdateConfirm-v590ext		CellUpdateConfirm-v590ext-IEs,
						v5d0NonCriticalExtenstions		SEQUENCE {
							cellUpdateConfirm-v5d0ext		CellUpdateConfirm-v5d0ext-IEs,
							v690NonCriticalExtensions		SEQUENCE {
								cellUpdateConfirm-v690ext		CellUpdateConfirm-v690ext-IEs,
								nonCriticalExtensions			SEQUENCE {} OPTIONAL
							}		OPTIONAL
						}		OPTIONAL
					}		OPTIONAL
				}		OPTIONAL
			}		OPTIONAL
		}		OPTIONAL
	},
	later-than-r3					SEQUENCE {
		rrc-TransactionIdentifier		RRC-TransactionIdentifier,
		criticalExtensions				CHOICE {
			r4								SEQUENCE {
				cellUpdateConfirm-r4			CellUpdateConfirm-r4-IEs,
				v4d0NonCriticalExtensions		SEQUENCE {
					-- Container for adding non critical extensions after freezing REL-5
					cellUpdateConfirm-r4-add-ext	BIT STRING		OPTIONAL,
					v590NonCriticalExtenstions		SEQUENCE {
						cellUpdateConfirm-v590ext		CellUpdateConfirm-v590ext-IEs,
						v5d0NonCriticalExtenstions		SEQUENCE {
							cellUpdateConfirm-v5d0ext		CellUpdateConfirm-v5d0ext-IEs,
							v690NonCriticalExtensions		SEQUENCE {
								cellUpdateConfirm-v690ext		CellUpdateConfirm-v690ext-IEs,
								nonCriticalExtensions			SEQUENCE {}		OPTIONAL
							}	OPTIONAL
						}	OPTIONAL
					}	OPTIONAL
				}	OPTIONAL
			},
			criticalExtensions				CHOICE {
				r5								SEQUENCE {
					cellUpdateConfirm-r5			CellUpdateConfirm-r5-IEs,
					-- Container for adding non critical extensions after freezing REL-6
					cellUpdateConfirm-r5-add-ext	BIT STRING		OPTIONAL,
					v5d0NonCriticalExtenstions		SEQUENCE {
						cellUpdateConfirm-v5d0ext		CellUpdateConfirm-v5d0ext-IEs,
						v690NonCriticalExtensions		SEQUENCE {
							cellUpdateConfirm-v690ext		CellUpdateConfirm-v690ext-IEs,
							nonCriticalExtensions			SEQUENCE {}		OPTIONAL
						}	OPTIONAL
					}	OPTIONAL
				},
				criticalExtensions				CHOICE {
					r6								SEQUENCE {
						cellUpdateConfirm-r6			CellUpdateConfirm-r6-IEs,
						-- Container for adding non critical extensions after freezing REL-7
						cellUpdateConfirm-r6-add-ext	BIT STRING		OPTIONAL,
						v6b0NonCriticalExtensions		SEQUENCE {
							cellUpdateConfirm-v6b0ext		CellUpdateConfirm-v6b0ext-IEs,
							nonCriticalExtensions			SEQUENCE {}		OPTIONAL
						}	OPTIONAL
					},
					criticalExtensions				CHOICE {
						r7								SEQUENCE {
							cellUpdateConfirm-r7			CellUpdateConfirm-r7-IEs,
							-- Container for adding non critical extensions after freezing REL-8
							cellUpdateConfirm-r7-add-ext	BIT STRING
										(CONTAINING CellUpdateConfirm-r7-add-ext-IEs)	OPTIONAL,
							v780NonCriticalExtensions		SEQUENCE {
								cellUpdateConfirm-v780ext		CellUpdateConfirm-v780ext-IEs,
								v860NonCriticalExtensions		SEQUENCE {
									cellUpdateConfirm-v860ext		CellUpdateConfirm-v860ext-IEs,
									nonCriticalExtensions			SEQUENCE {}		OPTIONAL
								}	OPTIONAL
							}	OPTIONAL
						},
						criticalExtensions				CHOICE {
							r8								SEQUENCE {
								cellUpdateConfirm-r8			CellUpdateConfirm-r8-IEs,
								-- Container for adding non critical extensions after freezing REL-9
								cellUpdateConfirm-r8-add-ext	BIT STRING		OPTIONAL,
								v7d0NonCriticalExtensions		SEQUENCE {
									cellUpdateConfirm-v7d0ext		CellUpdateConfirm-v7d0ext-IEs,
									v7f0NonCriticalExtensions		SEQUENCE {
										cellUpdateConfirm-v7f0ext	CellUpdateConfirm-v7f0ext-IEs,
										v890NonCriticalExtensions		SEQUENCE {
											cellUpdateConfirm-v890ext
															CellUpdateConfirm-v890ext-IEs,
											v7g0NonCriticalExtensions		SEQUENCE {
												cellUpdateConfirm-v7g0ext
															CellUpdateConfirm-v7g0ext-IEs,
												v8a0NonCriticalExtensions		SEQUENCE {
													cellUpdateConfirm-v8a0ext
																CellUpdateConfirm-v8a0ext-IEs,
													nonCriticalExtensions			SEQUENCE {}		OPTIONAL
												}	OPTIONAL
											}	OPTIONAL
										}	OPTIONAL
									}	OPTIONAL
								}	OPTIONAL
							},
							criticalExtensions				CHOICE {
								r9								SEQUENCE {
									cellUpdateConfirm-r9			CellUpdateConfirm-r9-IEs,
									-- Container for adding non critical extensions after 
									-- freezing REL-10
									cellUpdateConfirm-r9-add-ext	BIT STRING		OPTIONAL,
									v950NonCriticalExtensions		SEQUENCE {
										cellUpdateConfirm-v950ext		CellUpdateConfirm-v950ext-IEs,
										v9c0NonCriticalExtensions		SEQUENCE {
											cellUpdateConfirm-v9c0ext		CellUpdateConfirm-v9c0ext-IEs,
											nonCriticalExtensions			SEQUENCE {}		OPTIONAL
										}	OPTIONAL
									}	OPTIONAL
								},
								criticalExtensions				CHOICE {
									r10								SEQUENCE {
										cellUpdateConfirm-r10			CellUpdateConfirm-r10-IEs,
										-- Container for adding non critical extensions after 
										-- freezing REL-11
										cellUpdateConfirm-r10-add-ext	BIT STRING		OPTIONAL,
										v9c0NonCriticalExtensions		SEQUENCE {
											cellUpdateConfirm-v9c0ext		CellUpdateConfirm-v9c0ext-IEs,
											vb50NonCriticalExtensions		SEQUENCE {
												cellUpdateConfirm-vb50ext
																	CellUpdateConfirm-vb50ext-IEs,
												nonCriticalExtensions		SEQUENCE {}		OPTIONAL
											}	OPTIONAL
										}	OPTIONAL
									},
									criticalExtensions				CHOICE {
										r11								SEQUENCE {
											cellUpdateConfirm-r11			CellUpdateConfirm-r11-IEs,
											-- Container for adding non critical extensions after 
											-- freezing REL-12
											cellUpdateConfirm-r11-add-ext	
																			BIT STRING	OPTIONAL,
											nonCriticalExtensions			SEQUENCE {}		OPTIONAL
										},
										criticalExtensions				SEQUENCE {}
									}
								}
							}
						}
					}
				}
			}
		}
	}
}

CellUpdateConfirm-r3-IEs ::= SEQUENCE {
	-- User equipment IEs
		rrc-TransactionIdentifier		RRC-TransactionIdentifier,
		integrityProtectionModeInfo		IntegrityProtectionModeInfo			OPTIONAL,
		cipheringModeInfo				CipheringModeInfo					OPTIONAL,
		activationTime					ActivationTime						OPTIONAL,
		new-U-RNTI						U-RNTI								OPTIONAL,
		new-C-RNTI						C-RNTI								OPTIONAL,
		rrc-StateIndicator				RRC-StateIndicator,
		utran-DRX-CycleLengthCoeff		UTRAN-DRX-CycleLengthCoefficient	OPTIONAL,
		rlc-Re-establishIndicatorRb2-3or4		BOOLEAN,
		rlc-Re-establishIndicatorRb5orAbove		BOOLEAN,
	-- CN information elements
		cn-InformationInfo				CN-InformationInfo					OPTIONAL,
	-- UTRAN mobility IEs
		ura-Identity					URA-Identity						OPTIONAL,
	-- Radio bearer IEs
		rb-InformationReleaseList		RB-InformationReleaseList			OPTIONAL,
		rb-InformationReconfigList		RB-InformationReconfigList			OPTIONAL,
		rb-InformationAffectedList		RB-InformationAffectedList			OPTIONAL,
		dl-CounterSynchronisationInfo	DL-CounterSynchronisationInfo		OPTIONAL,
	-- Transport channel IEs
		ul-CommonTransChInfo			UL-CommonTransChInfo				OPTIONAL,
		ul-deletedTransChInfoList		UL-DeletedTransChInfoList			OPTIONAL,
		ul-AddReconfTransChInfoList		UL-AddReconfTransChInfoList			OPTIONAL,
		modeSpecificTransChInfo			CHOICE {
			fdd								SEQUENCE {
				-- dummy and dummy2 are not used in this version of the specification, they should
				-- not be sent and if received they should be ignored.
				dummy							CPCH-SetID					OPTIONAL,
				dummy2							DRAC-StaticInformationList	OPTIONAL
			},
			tdd								NULL
		},
		dl-CommonTransChInfo			DL-CommonTransChInfo				OPTIONAL,
		dl-DeletedTransChInfoList		DL-DeletedTransChInfoList			OPTIONAL,
		dl-AddReconfTransChInfoList		DL-AddReconfTransChInfoList			OPTIONAL,
	-- Physical channel IEs
		frequencyInfo					FrequencyInfo						OPTIONAL,
		maxAllowedUL-TX-Power			MaxAllowedUL-TX-Power				OPTIONAL,
		ul-ChannelRequirement			UL-ChannelRequirement				OPTIONAL,
		modeSpecificPhysChInfo			CHOICE {
			fdd								SEQUENCE {
				-- dummy is not used in this version of specification, it should
				-- not be sent and if received it should be ignored.
				dummy							DL-PDSCH-Information		OPTIONAL
			},
			tdd								NULL
		},
		dl-CommonInformation			DL-CommonInformation				OPTIONAL,
		dl-InformationPerRL-List		DL-InformationPerRL-List			OPTIONAL
}

CellUpdateConfirm-v3a0ext ::= SEQUENCE {
	-- The IE "new-DSCH-RNTI" should not be included in FDD mode, and if received the UE behaviour
	-- is unspecified
	new-DSCH-RNTI				DSCH-RNTI								OPTIONAL
}

CellUpdateConfirm-v4b0ext-IEs ::= SEQUENCE {
	-- Physical channel IEs
		-- dummy is not used in this version of the specification, it should
		-- not be sent and if received it should be ignored.
		dummy								SSDT-UL								OPTIONAL,
		-- The order of the RLs in IE cell-id-PerRL-List is the same as
		-- in IE DL-InformationPerRL-List included in this message
		cell-id-PerRL-List					CellIdentity-PerRL-List				OPTIONAL
}

CellUpdateConfirm-v590ext-IEs ::= SEQUENCE {
	-- Physical channel IEs
		dl-TPC-PowerOffsetPerRL-List	DL-TPC-PowerOffsetPerRL-List		OPTIONAL
}

CellUpdateConfirm-v5d0ext-IEs ::=	SEQUENCE {
	--Radio Bearer IEs
		pdcp-ROHC-TargetMode			PDCP-ROHC-TargetMode				OPTIONAL
}
CellUpdateConfirm-r4-IEs ::= SEQUENCE {
	-- User equipment IEs
		integrityProtectionModeInfo		IntegrityProtectionModeInfo			OPTIONAL,
		cipheringModeInfo				CipheringModeInfo					OPTIONAL,
		activationTime					ActivationTime						OPTIONAL,
		new-U-RNTI						U-RNTI								OPTIONAL,
		new-C-RNTI						C-RNTI								OPTIONAL,
		-- The IE "new-DSCH-RNTI" should not be included in FDD mode, and if received
		-- the UE behaviour is unspecified
		new-DSCH-RNTI					DSCH-RNTI							OPTIONAL,
		rrc-StateIndicator				RRC-StateIndicator,
		utran-DRX-CycleLengthCoeff		UTRAN-DRX-CycleLengthCoefficient	OPTIONAL,
		rlc-Re-establishIndicatorRb2-3or4		BOOLEAN,
		rlc-Re-establishIndicatorRb5orAbove	BOOLEAN,
	-- CN information elements
		cn-InformationInfo				CN-InformationInfo					OPTIONAL,
	-- UTRAN mobility IEs
		ura-Identity					URA-Identity						OPTIONAL,
	-- Radio bearer IEs
		rb-InformationReleaseList		RB-InformationReleaseList			OPTIONAL,
		rb-InformationReconfigList		RB-InformationReconfigList-r4		OPTIONAL,
		rb-InformationAffectedList		RB-InformationAffectedList			OPTIONAL,
		dl-CounterSynchronisationInfo	DL-CounterSynchronisationInfo		OPTIONAL,
	-- Transport channel IEs
		ul-CommonTransChInfo			UL-CommonTransChInfo-r4				OPTIONAL,
		ul-deletedTransChInfoList		UL-DeletedTransChInfoList			OPTIONAL,
		ul-AddReconfTransChInfoList		UL-AddReconfTransChInfoList			OPTIONAL,
		modeSpecificTransChInfo			CHOICE {
			fdd								SEQUENCE {
				-- dummy and dummy2 are not used in this version of the specification, they should
				-- not be sent and if received they should be ignored.
				dummy							CPCH-SetID					OPTIONAL,
				dummy2							DRAC-StaticInformationList	OPTIONAL
			},
			tdd								NULL
		},
		dl-CommonTransChInfo			DL-CommonTransChInfo-r4				OPTIONAL,
		dl-DeletedTransChInfoList		DL-DeletedTransChInfoList			OPTIONAL,
		dl-AddReconfTransChInfoList		DL-AddReconfTransChInfoList-r4		OPTIONAL,
	-- Physical channel IEs
		frequencyInfo					FrequencyInfo						OPTIONAL,
		maxAllowedUL-TX-Power			MaxAllowedUL-TX-Power				OPTIONAL,
		ul-ChannelRequirement			UL-ChannelRequirement-r4			OPTIONAL,
		modeSpecificPhysChInfo			CHOICE {
			fdd								SEQUENCE {
				-- dummy is not used in this version of specification, it should
				-- not be sent and if received it should be ignored.
				dummy							DL-PDSCH-Information		OPTIONAL
			},
			tdd								NULL
		},
		dl-CommonInformation			DL-CommonInformation-r4				OPTIONAL,
		dl-InformationPerRL-List		DL-InformationPerRL-List-r4			OPTIONAL
}

CellUpdateConfirm-r5-IEs ::= SEQUENCE {
	-- User equipment IEs
		integrityProtectionModeInfo		IntegrityProtectionModeInfo			OPTIONAL,
		cipheringModeInfo				CipheringModeInfo					OPTIONAL,
		activationTime					ActivationTime						OPTIONAL,
		new-U-RNTI						U-RNTI								OPTIONAL,
		new-C-RNTI						C-RNTI								OPTIONAL,
		-- The IE "new-DSCH-RNTI" should not be included in FDD mode, and if received
		-- the UE behaviour is unspecified
		new-DSCH-RNTI					DSCH-RNTI							OPTIONAL,
		new-H-RNTI						H-RNTI								OPTIONAL,
		rrc-StateIndicator				RRC-StateIndicator,
		utran-DRX-CycleLengthCoeff		UTRAN-DRX-CycleLengthCoefficient	OPTIONAL,
		rlc-Re-establishIndicatorRb2-3or4		BOOLEAN,
		rlc-Re-establishIndicatorRb5orAbove	BOOLEAN,
	-- CN information elements
		cn-InformationInfo				CN-InformationInfo					OPTIONAL,
	-- UTRAN mobility IEs
		ura-Identity					URA-Identity						OPTIONAL,
	-- Radio bearer IEs
		rb-InformationReleaseList		RB-InformationReleaseList			OPTIONAL,
		rb-InformationReconfigList		RB-InformationReconfigList-r5		OPTIONAL,
		rb-InformationAffectedList		RB-InformationAffectedList-r5		OPTIONAL,
		dl-CounterSynchronisationInfo	DL-CounterSynchronisationInfo-r5	OPTIONAL,
	-- Transport channel IEs
		ul-CommonTransChInfo			UL-CommonTransChInfo-r4				OPTIONAL,
		ul-deletedTransChInfoList		UL-DeletedTransChInfoList			OPTIONAL,
		ul-AddReconfTransChInfoList		UL-AddReconfTransChInfoList			OPTIONAL,
		modeSpecificTransChInfo			CHOICE {
			fdd								SEQUENCE {
				-- dummy and dummy2 are not used in this version of the specification, they should
				-- not be sent and if received they should be ignored.
				dummy							CPCH-SetID					OPTIONAL,
				dummy2							DRAC-StaticInformationList	OPTIONAL
			},
			tdd								NULL
		},
		dl-CommonTransChInfo			DL-CommonTransChInfo-r4				OPTIONAL,
		dl-DeletedTransChInfoList		DL-DeletedTransChInfoList-r5		OPTIONAL,
		dl-AddReconfTransChInfoList		DL-AddReconfTransChInfoList-r5		OPTIONAL,
	-- Physical channel IEs
		frequencyInfo					FrequencyInfo						OPTIONAL,
		maxAllowedUL-TX-Power			MaxAllowedUL-TX-Power				OPTIONAL,
		ul-ChannelRequirement			UL-ChannelRequirement-r5			OPTIONAL,
		modeSpecificPhysChInfo			CHOICE {
			fdd								SEQUENCE {
				-- dummy is not used in this version of specification, it should
				-- not be sent and if received it should be ignored.
				dummy							DL-PDSCH-Information		OPTIONAL
			},
			tdd								NULL
		},
		dl-HSPDSCH-Information			DL-HSPDSCH-Information				OPTIONAL,
		dl-CommonInformation			DL-CommonInformation-r5				OPTIONAL,
		dl-InformationPerRL-List		DL-InformationPerRL-List-r5			OPTIONAL
}

CellUpdateConfirm-r6-IEs ::= SEQUENCE {
	-- User equipment IEs
		integrityProtectionModeInfo		IntegrityProtectionModeInfo			OPTIONAL,
		cipheringModeInfo				CipheringModeInfo					OPTIONAL,
		activationTime					ActivationTime						OPTIONAL,
		new-U-RNTI						U-RNTI								OPTIONAL,
		new-C-RNTI						C-RNTI								OPTIONAL,
		-- The IE "new-DSCH-RNTI" should not be included in FDD mode,
		-- and if received the UE behaviour is unspecified
		new-DSCH-RNTI					DSCH-RNTI							OPTIONAL,
		new-H-RNTI						H-RNTI								OPTIONAL,
		newPrimary-E-RNTI				E-RNTI								OPTIONAL,
		newSecondary-E-RNTI				E-RNTI								OPTIONAL,
		rrc-StateIndicator				RRC-StateIndicator,
		utran-DRX-CycleLengthCoeff		UTRAN-DRX-CycleLengthCoefficient	OPTIONAL,
		rlc-Re-establishIndicatorRb2-3or4		BOOLEAN,
		rlc-Re-establishIndicatorRb5orAbove		BOOLEAN,
	-- CN information elements
		cn-InformationInfo				CN-InformationInfo-r6				OPTIONAL,
	-- UTRAN mobility IEs
		ura-Identity					URA-Identity						OPTIONAL,
	-- Radio bearer IEs
		rb-InformationReleaseList		RB-InformationReleaseList			OPTIONAL,
		rb-InformationReconfigList		RB-InformationReconfigList-r6		OPTIONAL,
		rb-InformationAffectedList		RB-InformationAffectedList-r6		OPTIONAL,
		dl-CounterSynchronisationInfo	DL-CounterSynchronisationInfo-r5	OPTIONAL,
		pdcp-ROHC-TargetMode			PDCP-ROHC-TargetMode				OPTIONAL,
	-- Transport channel IEs
		ul-CommonTransChInfo			UL-CommonTransChInfo-r4				OPTIONAL,
		ul-deletedTransChInfoList		UL-DeletedTransChInfoList-r6		OPTIONAL,
		ul-AddReconfTransChInfoList		UL-AddReconfTransChInfoList-r6		OPTIONAL,
		dl-CommonTransChInfo			DL-CommonTransChInfo-r4				OPTIONAL,
		dl-DeletedTransChInfoList		DL-DeletedTransChInfoList-r5		OPTIONAL,
		dl-AddReconfTransChInfoList		DL-AddReconfTransChInfoList-r5		OPTIONAL,
	-- Physical channel IEs
		frequencyInfo					FrequencyInfo						OPTIONAL,
		maxAllowedUL-TX-Power			MaxAllowedUL-TX-Power				OPTIONAL,
		ul-DPCH-Info					UL-DPCH-Info-r6						OPTIONAL,
		ul-EDCH-Information				UL-EDCH-Information-r6				OPTIONAL,
		dl-HSPDSCH-Information			DL-HSPDSCH-Information-r6			OPTIONAL,
		dl-CommonInformation			DL-CommonInformation-r6				OPTIONAL,
		dl-InformationPerRL-List		DL-InformationPerRL-List-r6			OPTIONAL,
	-- MBMS IEs
		mbms-PL-ServiceRestrictInfo		MBMS-PL-ServiceRestrictInfo-r6		OPTIONAL
}

CellUpdateConfirm-v690ext-IEs ::=	SEQUENCE {
	-- Core network IEs
		primary-plmn-Identity			PLMN-Identity						OPTIONAL,
	-- Physical channel IEs
		-- The IE harq-Preamble-Mode should not be used in the r3 and r4 versions of the message
		-- If included in the r3 or r4 version of the message, the UE should ignore the IE
		harq-Preamble-Mode				HARQ-Preamble-Mode					OPTIONAL,
		beaconPLEst						BEACON-PL-Est						OPTIONAL,
		postVerificationPeriod			ENUMERATED { true }					OPTIONAL,
		dhs-sync						DHS-Sync							OPTIONAL,
	-- MBMS IEs
		mbms-PL-ServiceRestrictInfo		MBMS-PL-ServiceRestrictInfo-r6		OPTIONAL
}

CellUpdateConfirm-v6b0ext-IEs ::= SEQUENCE {
	-- Physical channel IEs
		dl-InformationPerRL-List-v6b0ext	DL-InformationPerRL-List-v6b0ext	OPTIONAL
}

CellUpdateConfirm-r7-IEs ::= SEQUENCE {
	-- User equipment IEs
		integrityProtectionModeInfo		IntegrityProtectionModeInfo-r7		OPTIONAL,
		cipheringModeInfo				CipheringModeInfo-r7				OPTIONAL,
		activationTime					ActivationTime						OPTIONAL,
		new-U-RNTI						U-RNTI								OPTIONAL,
		new-C-RNTI						C-RNTI								OPTIONAL,
		-- The IE "new-DSCH-RNTI" should not be included in FDD mode,
		-- and if received the UE behaviour is unspecified
		new-DSCH-RNTI					DSCH-RNTI							OPTIONAL,
		new-H-RNTI						H-RNTI								OPTIONAL,
		newPrimary-E-RNTI				E-RNTI								OPTIONAL,
		newSecondary-E-RNTI				E-RNTI								OPTIONAL,
		rrc-StateIndicator				RRC-StateIndicator,
		utran-DRX-CycleLengthCoeff		UTRAN-DRX-CycleLengthCoefficient-r7	OPTIONAL,
		waitTime						WaitTime							OPTIONAL,
		rlc-Re-establishIndicatorRb2-3or4		BOOLEAN,
		rlc-Re-establishIndicatorRb5orAbove		BOOLEAN,
	-- CN information elements
		cn-InformationInfo				CN-InformationInfo-r6				OPTIONAL,
	-- UTRAN mobility IEs
		ura-Identity					URA-Identity						OPTIONAL,
		supportForChangeOfUE-Capability	BOOLEAN								OPTIONAL,
	-- Radio bearer IEs
		rb-InformationReleaseList		RB-InformationReleaseList			OPTIONAL,
		rb-InformationReconfigList		RB-InformationReconfigList-r7		OPTIONAL,
		rb-InformationAffectedList		RB-InformationAffectedList-r7		OPTIONAL,
		dl-CounterSynchronisationInfo	DL-CounterSynchronisationInfo-r5	OPTIONAL,
		pdcp-ROHC-TargetMode			PDCP-ROHC-TargetMode				OPTIONAL,
	-- Transport channel IEs
		ul-CommonTransChInfo			UL-CommonTransChInfo-r4				OPTIONAL,
		ul-deletedTransChInfoList		UL-DeletedTransChInfoList-r6		OPTIONAL,
		ul-AddReconfTransChInfoList		UL-AddReconfTransChInfoList-r7		OPTIONAL,
		dl-CommonTransChInfo			DL-CommonTransChInfo-r4				OPTIONAL,
		dl-DeletedTransChInfoList		DL-DeletedTransChInfoList-r7		OPTIONAL,
		dl-AddReconfTransChInfoList		DL-AddReconfTransChInfoList-r7		OPTIONAL,
	-- Physical channel IEs
		frequencyInfo					FrequencyInfo						OPTIONAL,
		multi-frequencyInfo				Multi-frequencyInfo-LCR-r7			OPTIONAL,
		dtx-drx-TimingInfo				DTX-DRX-TimingInfo-r7				OPTIONAL,
		dtx-drx-Info					DTX-DRX-Info-r7						OPTIONAL,
		hs-scch-LessInfo				HS-SCCH-LessInfo-r7					OPTIONAL,
		mimoParameters					MIMO-Parameters-r7					OPTIONAL,
		maxAllowedUL-TX-Power			MaxAllowedUL-TX-Power				OPTIONAL,
		ul-DPCH-Info					UL-DPCH-Info-r7						OPTIONAL,
		ul-EDCH-Information				UL-EDCH-Information-r7				OPTIONAL,
		dl-HSPDSCH-Information			DL-HSPDSCH-Information-r7			OPTIONAL,
		dl-CommonInformation			DL-CommonInformation-r7				OPTIONAL,
		dl-InformationPerRL-List		DL-InformationPerRL-List-r7			OPTIONAL,
	-- MBMS IEs
		mbms-PL-ServiceRestrictInfo		MBMS-PL-ServiceRestrictInfo-r6		OPTIONAL
}

CellUpdateConfirm-r7-add-ext-IEs ::= SEQUENCE {
		cellUpdateConfirm-v7d0ext		CellUpdateConfirm-v7d0ext-IEs		OPTIONAL,
		v7f0NonCriticalExtensions		SEQUENCE {
			cellUpdateConfirm-v7f0ext		CellUpdateConfirm-v7f0ext-IEs,
			v7g0NonCriticalExtensions		SEQUENCE {
				cellUpdateConfirm-v7g0ext		CellUpdateConfirm-v7g0ext-IEs,
				nonCriticalExtensions			SEQUENCE {}		OPTIONAL
			}	OPTIONAL
		}	OPTIONAL
}

CellUpdateConfirm-v780ext-IEs ::= SEQUENCE {
	-- Physical channel IEs
		hs-DSCH-TBSizeTable				HS-DSCH-TBSizeTable					OPTIONAL
}

CellUpdateConfirm-v7d0ext-IEs ::=	SEQUENCE {
	-- Physical channel IEs
		ul-EDCH-Information				UL-EDCH-Information-ext				OPTIONAL
}

CellUpdateConfirm-v7f0ext-IEs ::= SEQUENCE {
	-- Physical channel IEs
		mimoParameters					MIMO-Parameters-v7f0ext				OPTIONAL
}

CellUpdateConfirm-v7g0ext-IEs ::= SEQUENCE {
	-- Physical channel IEs
		mimoParameters					MIMO-Parameters-v7g0ext				OPTIONAL
}

CellUpdateConfirm-r8-IEs ::= SEQUENCE {
	-- User equipment IEs
		integrityProtectionModeInfo		IntegrityProtectionModeInfo-r7		OPTIONAL,
		cipheringModeInfo				CipheringModeInfo-r7				OPTIONAL,
		activationTime					ActivationTime						OPTIONAL,
		new-U-RNTI						U-RNTI								OPTIONAL,
		new-C-RNTI						C-RNTI								OPTIONAL,
		-- The IE "new-DSCH-RNTI" should not be included in FDD mode,
		-- and if received the UE behaviour is unspecified
		new-DSCH-RNTI					DSCH-RNTI							OPTIONAL,
		new-H-RNTI						H-RNTI								OPTIONAL,
		newPrimary-E-RNTI				E-RNTI								OPTIONAL,
		newSecondary-E-RNTI				E-RNTI								OPTIONAL,
		rrc-StateIndicator				RRC-StateIndicator,
		utran-DRX-CycleLengthCoeff		UTRAN-DRX-CycleLengthCoefficient-r7	OPTIONAL,
		waitTime						WaitTime							OPTIONAL,
		rlc-Re-establishIndicatorRb2-3or4		BOOLEAN,
		rlc-Re-establishIndicatorRb5orAbove		BOOLEAN,
	-- CN information elements
		cn-InformationInfo				CN-InformationInfo-r6				OPTIONAL,
	-- UTRAN mobility IEs
		ura-Identity					URA-Identity						OPTIONAL,
		supportForChangeOfUE-Capability	BOOLEAN								OPTIONAL,
	-- Specification mode information
		-- dummy is not used in this version of the specification, it should
		-- not be sent and if received it should be ignored.
		dummy							DefaultConfigForCellFACH			OPTIONAL,
	-- Radio bearer IEs
		rab-InformationSetup			RAB-InformationSetup-r8				OPTIONAL,
		rb-InformationReleaseList		RB-InformationReleaseList			OPTIONAL,
		rb-InformationReconfigList		RB-InformationReconfigList-r8		OPTIONAL,
		rb-InformationAffectedList		RB-InformationAffectedList-r8		OPTIONAL,
		dl-CounterSynchronisationInfo	DL-CounterSynchronisationInfo-r5	OPTIONAL,
		pdcp-ROHC-TargetMode			PDCP-ROHC-TargetMode				OPTIONAL,
	-- Transport channel IEs
		ul-CommonTransChInfo			UL-CommonTransChInfo-r4				OPTIONAL,
		ul-deletedTransChInfoList		UL-DeletedTransChInfoList-r6		OPTIONAL,
		ul-AddReconfTransChInfoList		UL-AddReconfTransChInfoList-r8		OPTIONAL,
		dl-CommonTransChInfo			DL-CommonTransChInfo-r4				OPTIONAL,
		dl-DeletedTransChInfoList		DL-DeletedTransChInfoList-r7		OPTIONAL,
		dl-AddReconfTransChInfoList		DL-AddReconfTransChInfoList-r7		OPTIONAL,
	-- Physical channel IEs
		frequencyInfo					FrequencyInfo						OPTIONAL,
		multi-frequencyInfo				Multi-frequencyInfo-LCR-r7			OPTIONAL,
		dtx-drx-TimingInfo				DTX-DRX-TimingInfo-r7				OPTIONAL,
		dtx-drx-Info					DTX-DRX-Info-r7						OPTIONAL,
		hs-scch-LessInfo				HS-SCCH-LessInfo-r7					OPTIONAL,
		mimoParameters					MIMO-Parameters-r8					OPTIONAL,
		maxAllowedUL-TX-Power			MaxAllowedUL-TX-Power				OPTIONAL,
		ul-DPCH-Info					UL-DPCH-Info-r7						OPTIONAL,
		ul-EDCH-Information				UL-EDCH-Information-r8				OPTIONAL,
		dl-HSPDSCH-Information			DL-HSPDSCH-Information-r8			OPTIONAL,
		dl-CommonInformation			DL-CommonInformation-r8				OPTIONAL,
		dl-InformationPerRL-List		DL-InformationPerRL-List-r8			OPTIONAL,
		dl-SecondaryCellInfoFDD			DL-SecondaryCellInfoFDD				OPTIONAL,
		controlChannelDRXInfo-TDD128	ControlChannelDRXInfo-TDD128-r8		OPTIONAL,
		sps-Information-TDD128			SPS-Information-TDD128-r8			OPTIONAL,
	-- MBMS IEs
		mbms-PL-ServiceRestrictInfo		MBMS-PL-ServiceRestrictInfo-r6		OPTIONAL
}

CellUpdateConfirm-v860ext-IEs ::=	SEQUENCE {
		rab-InformationSetup			SEQUENCE {
			rab-InformationSetup-r7			RAB-InformationSetup-r7,
			rab-InformationSetup-v820ext	RAB-InformationSetup-v820ext
		}		OPTIONAL
}

CellUpdateConfirm-v890ext-IEs ::= SEQUENCE {
	-- Physical channel IEs
		dl-SecondaryCellInfoFDD-v890ext		DL-SecondaryCellInfoFDD-v890ext		OPTIONAL,
		dl-HSPDSCH-Information				DL-HSPDSCH-Information-r8-ext		OPTIONAL
}

CellUpdateConfirm-v8a0ext-IEs ::= SEQUENCE {
	-- Physical channel IEs
		dl-HSPDSCH-Information				DL-HSPDSCH-Information-r8-ext2		OPTIONAL
}

CellUpdateConfirm-r9-IEs ::= SEQUENCE {
	-- User equipment IEs
		integrityProtectionModeInfo		IntegrityProtectionModeInfo-r7		OPTIONAL,
		cipheringModeInfo				CipheringModeInfo-r7				OPTIONAL,
		activationTime					ActivationTime						OPTIONAL,
		new-U-RNTI						U-RNTI								OPTIONAL,
		new-C-RNTI						C-RNTI								OPTIONAL,
		-- The IE "new-DSCH-RNTI" should not be included in FDD mode,
		-- and if received the UE behaviour is unspecified
		new-DSCH-RNTI					DSCH-RNTI							OPTIONAL,
		new-H-RNTI						H-RNTI								OPTIONAL,
		newPrimary-E-RNTI				E-RNTI								OPTIONAL,
		newSecondary-E-RNTI				E-RNTI								OPTIONAL,
		rrc-StateIndicator				RRC-StateIndicator,
		utran-DRX-CycleLengthCoeff		UTRAN-DRX-CycleLengthCoefficient-r7	OPTIONAL,
		waitTime						WaitTime							OPTIONAL,
		rlc-Re-establishIndicatorRb2-3or4		BOOLEAN,
		rlc-Re-establishIndicatorRb5orAbove		BOOLEAN,
	-- CN information elements
		cn-InformationInfo				CN-InformationInfo-r6				OPTIONAL,
	-- UTRAN mobility IEs
		ura-Identity					URA-Identity						OPTIONAL,
		supportForChangeOfUE-Capability	BOOLEAN								OPTIONAL,
	-- Specification mode information
		-- dummy is not used in this version of the specification, it should
		-- not be sent and if received it should be ignored.
		dummy							DefaultConfigForCellFACH			OPTIONAL,
	-- Radio bearer IEs
		rab-InformationSetup			RAB-InformationSetup-r8				OPTIONAL,
		rb-InformationReleaseList		RB-InformationReleaseList			OPTIONAL,
		rb-InformationReconfigList		RB-InformationReconfigList-r8		OPTIONAL,
		rb-InformationAffectedList		RB-InformationAffectedList-r8		OPTIONAL,
		dl-CounterSynchronisationInfo	DL-CounterSynchronisationInfo-r5	OPTIONAL,
		pdcp-ROHC-TargetMode			PDCP-ROHC-TargetMode				OPTIONAL,
	-- Transport channel IEs
		ul-CommonTransChInfo			UL-CommonTransChInfo-r4				OPTIONAL,
		ul-deletedTransChInfoList		UL-DeletedTransChInfoList-r6		OPTIONAL,
		ul-AddReconfTransChInfoList		UL-AddReconfTransChInfoList-r8		OPTIONAL,
		dl-CommonTransChInfo			DL-CommonTransChInfo-r4				OPTIONAL,
		dl-DeletedTransChInfoList		DL-DeletedTransChInfoList-r7		OPTIONAL,
		dl-AddReconfTransChInfoList		DL-AddReconfTransChInfoList-r9		OPTIONAL,
	-- Physical channel IEs
		frequencyInfo					FrequencyInfo						OPTIONAL,
		multi-frequencyInfo				Multi-frequencyInfo-LCR-r7			OPTIONAL,
		dtx-drx-TimingInfo				DTX-DRX-TimingInfo-r7				OPTIONAL,
		dtx-drx-Info					DTX-DRX-Info-r7						OPTIONAL,
		hs-scch-LessInfo				HS-SCCH-LessInfo-r7					OPTIONAL,
		mimoParameters					MIMO-Parameters-r9					OPTIONAL,
		maxAllowedUL-TX-Power			MaxAllowedUL-TX-Power				OPTIONAL,
		ul-DPCH-Info					UL-DPCH-Info-r7						OPTIONAL,
		ul-EDCH-Information				UL-EDCH-Information-r9				OPTIONAL,
		ul-SecondaryCellInfoFDD			UL-SecondaryCellInfoFDD				OPTIONAL,
		dl-HSPDSCH-Information			DL-HSPDSCH-Information-r9			OPTIONAL,
		dl-CommonInformation			DL-CommonInformation-r8				OPTIONAL,
		dl-InformationPerRL-List		DL-InformationPerRL-List-r8			OPTIONAL,
		dl-SecondaryCellInfoFDD			DL-SecondaryCellInfoFDD-r9			OPTIONAL,
		controlChannelDRXInfo-TDD128	ControlChannelDRXInfo-TDD128-r8		OPTIONAL,
		sps-Information-TDD128			SPS-Information-TDD128-r8			OPTIONAL,
	-- MBMS IEs
		mbms-PL-ServiceRestrictInfo		MBMS-PL-ServiceRestrictInfo-r6		OPTIONAL,
	-- Measurement IEs for LCR
		cellDCHMeasOccasionInfo-TDD128	CellDCHMeasOccasionInfo-TDD128-r9	OPTIONAL
}

CellUpdateConfirm-v950ext-IEs ::= SEQUENCE {
	-- Physical channel IEs
		secondaryCellMimoParameters		SecondaryCellMIMOparametersFDD-v950ext		OPTIONAL
}

CellUpdateConfirm-v9c0ext-IEs ::= SEQUENCE {
	-- For 1.28Mcps TDD only
		dl-AddReconfTransChInfoList		DL-AddReconfTransChInfoList-TDD128-v9c0ext			OPTIONAL
}

CellUpdateConfirm-r10-IEs ::= SEQUENCE {
	-- User equipment IEs
		integrityProtectionModeInfo		IntegrityProtectionModeInfo-r7		OPTIONAL,
		cipheringModeInfo				CipheringModeInfo-r7				OPTIONAL,
		-- dummy2 is not used in this version of the specification, it should
		-- not be sent.
		dummy2							SR-VCC-Info							OPTIONAL,
		activationTime					ActivationTime						OPTIONAL,
		new-U-RNTI						U-RNTI								OPTIONAL,
		new-C-RNTI						C-RNTI								OPTIONAL,
		-- The IE "new-DSCH-RNTI" should not be included in FDD mode,
		-- and if received the UE behaviour is unspecified
		new-DSCH-RNTI					DSCH-RNTI							OPTIONAL,
		new-H-RNTI						H-RNTI								OPTIONAL,
		newPrimary-E-RNTI				E-RNTI								OPTIONAL,
		newSecondary-E-RNTI				E-RNTI								OPTIONAL,
		rrc-StateIndicator				RRC-StateIndicator,
		utran-DRX-CycleLengthCoeff		UTRAN-DRX-CycleLengthCoefficient-r7	OPTIONAL,
		waitTime						WaitTime							OPTIONAL,
		rlc-Re-establishIndicatorRb2-3or4		BOOLEAN,
		rlc-Re-establishIndicatorRb5orAbove		BOOLEAN,
	-- CN information elements
		cn-InformationInfo				CN-InformationInfo-r6				OPTIONAL,
	-- UTRAN mobility IEs
		ura-Identity					URA-Identity						OPTIONAL,
		supportForChangeOfUE-Capability	BOOLEAN								OPTIONAL,
	-- Specification mode information
		-- dummy is not used in this version of the specification, it should
		-- not be sent and if received it should be ignored.
		dummy							DefaultConfigForCellFACH			OPTIONAL,
	-- Radio bearer IEs
		rab-InformationSetup			RAB-InformationSetup-r8				OPTIONAL,
		rb-InformationReleaseList		RB-InformationReleaseList			OPTIONAL,
		rb-InformationReconfigList		RB-InformationReconfigList-r8		OPTIONAL,
		rb-InformationAffectedList		RB-InformationAffectedList-r8		OPTIONAL,
		dl-CounterSynchronisationInfo	DL-CounterSynchronisationInfo-r5	OPTIONAL,
		pdcp-ROHC-TargetMode			PDCP-ROHC-TargetMode				OPTIONAL,
	-- Transport channel IEs
		ul-CommonTransChInfo			UL-CommonTransChInfo-r4				OPTIONAL,
		ul-deletedTransChInfoList		UL-DeletedTransChInfoList-r6		OPTIONAL,
		ul-AddReconfTransChInfoList		UL-AddReconfTransChInfoList-r8		OPTIONAL,
		dl-CommonTransChInfo			DL-CommonTransChInfo-r4				OPTIONAL,
		dl-DeletedTransChInfoList		DL-DeletedTransChInfoList-r7		OPTIONAL,
		dl-AddReconfTransChInfoList		DL-AddReconfTransChInfoList-r9		OPTIONAL,
	-- Physical channel IEs
		frequencyInfo					FrequencyInfo						OPTIONAL,
		multi-frequencyInfo				Multi-frequencyInfo-LCR-r7			OPTIONAL,
		dtx-drx-TimingInfo				DTX-DRX-TimingInfo-r7				OPTIONAL,
		dtx-drx-Info					DTX-DRX-Info-r7						OPTIONAL,
		hs-scch-LessInfo				HS-SCCH-LessInfo-r7					OPTIONAL,
		mimoParameters					MIMO-Parameters-r9					OPTIONAL,
		maxAllowedUL-TX-Power			MaxAllowedUL-TX-Power				OPTIONAL,
		ul-DPCH-Info					UL-DPCH-Info-r7						OPTIONAL,
		ul-EDCH-Information				UL-EDCH-Information-r9				OPTIONAL,
		ul-SecondaryCellInfoFDD			UL-SecondaryCellInfoFDD				OPTIONAL,
		ul-MulticarrierEDCHInfo-TDD128	UL-MulticarrierEDCHInfo-TDD128		OPTIONAL,
		dl-HSPDSCH-Information			DL-HSPDSCH-Information-r9			OPTIONAL,
		dl-CommonInformation			DL-CommonInformation-r10			OPTIONAL,
		dl-InformationPerRL-List		DL-InformationPerRL-List-r8			OPTIONAL,
		dl-SecondaryCellInfoFDD			DL-SecondaryCellInfoFDD-r10			OPTIONAL,
		additionalDLSecCellInfoListFDD	AdditionalDLSecCellInfoListFDD		OPTIONAL,
		controlChannelDRXInfo-TDD128	ControlChannelDRXInfo-TDD128-r8		OPTIONAL,
		sps-Information-TDD128			SPS-Information-TDD128-r8			OPTIONAL,
		mu-MIMO-Info-TDD128				MU-MIMO-Info-TDD128					OPTIONAL,
	-- MBMS IEs
		mbms-PL-ServiceRestrictInfo		MBMS-PL-ServiceRestrictInfo-r6		OPTIONAL,
	-- Measurement IEs for LCR
		cellDCHMeasOccasionInfo-TDD128	CellDCHMeasOccasionInfo-TDD128-r9	OPTIONAL
}

CellUpdateConfirm-vb50ext-IEs ::= SEQUENCE {
		ulOLTDInfoFDD						UL-OLTD-InfoFDD			OPTIONAL
}

CellUpdateConfirm-r11-IEs ::= SEQUENCE {
	-- User equipment IEs
		integrityProtectionModeInfo		IntegrityProtectionModeInfo-r7		OPTIONAL,
		cipheringModeInfo				CipheringModeInfo-r7				OPTIONAL,
		-- dummy2 is not used in this version of the specification, it should
		-- not be sent.
		dummy2							SR-VCC-Info							OPTIONAL,
		activationTime					ActivationTime						OPTIONAL,
		new-U-RNTI						U-RNTI								OPTIONAL,
		new-C-RNTI						C-RNTI								OPTIONAL,
		-- The IE "new-DSCH-RNTI" should not be included in FDD mode,
		-- and if received the UE behaviour is unspecified
		new-DSCH-RNTI					DSCH-RNTI							OPTIONAL,
		new-H-RNTI						H-RNTI								OPTIONAL,
		newPrimary-E-RNTI				E-RNTI								OPTIONAL,
		newSecondary-E-RNTI				E-RNTI								OPTIONAL,
		rrc-StateIndicator				RRC-StateIndicator,
		utran-DRX-CycleLengthCoeff		UTRAN-DRX-CycleLengthCoefficient-r7	OPTIONAL,
		waitTime						WaitTime							OPTIONAL,
		rlc-Re-establishIndicatorRb2-3or4		BOOLEAN,
		rlc-Re-establishIndicatorRb5orAbove		BOOLEAN,
	-- CN information elements
		cn-InformationInfo				CN-InformationInfo-r6				OPTIONAL,
	-- UTRAN mobility IEs
		ura-Identity					URA-Identity						OPTIONAL,
		supportForChangeOfUE-Capability	BOOLEAN								OPTIONAL,
	-- Specification mode information
		-- dummy is not used in this version of the specification, it should
		-- not be sent and if received it should be ignored.
		dummy							DefaultConfigForCellFACH			OPTIONAL,
	-- Radio bearer IEs
		rab-InformationSetup			RAB-InformationSetup-r8				OPTIONAL,
		rb-InformationReleaseList		RB-InformationReleaseList			OPTIONAL,
		rb-InformationReconfigList		RB-InformationReconfigList-r11		OPTIONAL,
		rb-InformationAffectedList		RB-InformationAffectedList-r8		OPTIONAL,
		dl-CounterSynchronisationInfo	DL-CounterSynchronisationInfo-r5	OPTIONAL,
		pdcp-ROHC-TargetMode			PDCP-ROHC-TargetMode				OPTIONAL,
	-- Transport channel IEs
		ul-CommonTransChInfo			UL-CommonTransChInfo-r4				OPTIONAL,
		ul-deletedTransChInfoList		UL-DeletedTransChInfoList-r6		OPTIONAL,
		ul-AddReconfTransChInfoList		UL-AddReconfTransChInfoList-r8		OPTIONAL,
		dl-CommonTransChInfo			DL-CommonTransChInfo-r4				OPTIONAL,
		dl-DeletedTransChInfoList		DL-DeletedTransChInfoList-r7		OPTIONAL,
		dl-AddReconfTransChInfoList		DL-AddReconfTransChInfoList-r11		OPTIONAL,
	-- Physical channel IEs
		frequencyInfo					FrequencyInfo						OPTIONAL,
		multi-frequencyInfo				Multi-frequencyInfo-LCR-r7			OPTIONAL,
		dtx-drx-TimingInfo				DTX-DRX-TimingInfo-r7				OPTIONAL,
		dtx-drx-Info					DTX-DRX-Info-r7						OPTIONAL,
		hs-scch-LessInfo				HS-SCCH-LessInfo-r7					OPTIONAL,
		mimoParameters					MIMO-Parameters-r9					OPTIONAL,
		mimo4x4Parameters				MIMO4x4-Parameters					OPTIONAL,
		maxAllowedUL-TX-Power			MaxAllowedUL-TX-Power				OPTIONAL,
		ul-DPCH-Info					UL-DPCH-Info-r11						OPTIONAL,
		ul-EDCH-Information				UL-EDCH-Information-r11				OPTIONAL,
		ul-SecondaryCellInfoFDD			UL-SecondaryCellInfoFDD				OPTIONAL,
		ul-MulticarrierEDCHInfo-TDD128	UL-MulticarrierEDCHInfo-TDD128		OPTIONAL,
		ul-CLTD-InfoFDD					UL-CLTD-InfoFDD						OPTIONAL,
		ul-OLTD-InfoFDD					UL-OLTD-InfoFDD		OPTIONAL,
		dl-HSPDSCH-Information			DL-HSPDSCH-Information-r11			OPTIONAL,
		dl-CommonInformation			DL-CommonInformation-r11			OPTIONAL,
		dl-InformationPerRL-List		DL-InformationPerRL-List-r11			OPTIONAL,
		dl-SecondaryCellInfoFDD			DL-SecondaryCellInfoFDD-r11			OPTIONAL,
		additionalDLSecCellInfoListFDD	AdditionalDLSecCellInfoListFDD-r11	OPTIONAL,
		additionalDLSecCellInfoListFDD2	AdditionalDLSecCellInfoListFDD2		OPTIONAL,
		commonERGCHInfoFDD				CommonERGCHInfoFDD					OPTIONAL,
		controlChannelDRXInfo-TDD128	ControlChannelDRXInfo-TDD128-r8		OPTIONAL,
		sps-Information-TDD128			SPS-Information-TDD128-r8			OPTIONAL,
		mu-MIMO-Info-TDD128				MU-MIMO-Info-TDD128					OPTIONAL,
	-- MBMS IEs
		mbms-PL-ServiceRestrictInfo		MBMS-PL-ServiceRestrictInfo-r6		OPTIONAL,
	-- Measurement IEs for LCR
		cellDCHMeasOccasionInfo-TDD128	CellDCHMeasOccasionInfo-TDD128-r9	OPTIONAL
}

-- ***************************************************
--
-- CELL UPDATE CONFIRM for CCCH
--
-- ***************************************************

CellUpdateConfirm-CCCH ::= CHOICE {
	r3								SEQUENCE {
		-- User equipment IEs
			u-RNTI						U-RNTI,
		-- The rest of the message is identical to the one sent on DCCH.
			cellUpdateConfirm-r3				CellUpdateConfirm-r3-IEs,
			laterNonCriticalExtensions		SEQUENCE {
				-- Container for additional R99 extensions
				cellUpdateConfirm-CCCH-r3-add-ext			BIT STRING	OPTIONAL,
				v4b0NonCriticalExtensions		SEQUENCE {
					cellUpdateConfirm-v4b0ext		CellUpdateConfirm-v4b0ext-IEs,
					v590NonCriticalExtensions		SEQUENCE {
						cellUpdateConfirm-v590ext		CellUpdateConfirm-v590ext-IEs,
						v5d0NonCriticalExtenstions		SEQUENCE {
							cellUpdateConfirm-v5d0ext		CellUpdateConfirm-v5d0ext-IEs,
							v690NonCriticalExtensions		SEQUENCE {
								cellUpdateConfirm-v690ext		CellUpdateConfirm-v690ext-IEs,
								nonCriticalExtensions			SEQUENCE {} OPTIONAL
							}	OPTIONAL
						}	OPTIONAL
					}	OPTIONAL
				}	OPTIONAL
			}	OPTIONAL
	},
	later-than-r3					SEQUENCE {
		u-RNTI							U-RNTI,
		rrc-TransactionIdentifier		RRC-TransactionIdentifier,
		criticalExtensions				CHOICE {
			r4								SEQUENCE {
				-- The rest of the message is identical to the one sent on DCCH.
				cellUpdateConfirm-r4			CellUpdateConfirm-r4-IEs,
				v4d0NonCriticalExtensions			SEQUENCE {
					-- Container for adding non critical extensions after freezing REL-5
					cellUpdateConfirm-CCCH-r4-add-ext		BIT STRING		OPTIONAL,
					v590NonCriticalExtensions		SEQUENCE {
						cellUpdateConfirm-v590ext		CellUpdateConfirm-v590ext-IEs,
						v5d0NonCriticalExtenstions		SEQUENCE {
							cellUpdateConfirm-v5d0ext		CellUpdateConfirm-v5d0ext-IEs,
							v690NonCriticalExtensions		SEQUENCE {
								cellUpdateConfirm-v690ext		CellUpdateConfirm-v690ext-IEs,
								nonCriticalExtensions			SEQUENCE {}		OPTIONAL
							}	OPTIONAL
						}	OPTIONAL
					}	OPTIONAL
				}	OPTIONAL
			},
			criticalExtensions				CHOICE {
				r5								SEQUENCE {
					cellUpdateConfirm-r5			CellUpdateConfirm-r5-IEs,
					cellUpdateConfirm-CCCH-r5-add-ext		BIT STRING		OPTIONAL,
					v5d0NonCriticalExtenstions		SEQUENCE {
						cellUpdateConfirm-v5d0ext		CellUpdateConfirm-v5d0ext-IEs,
						v690NonCriticalExtensions		SEQUENCE {
							cellUpdateConfirm-v690ext		CellUpdateConfirm-v690ext-IEs,
							nonCriticalExtensions			SEQUENCE {}		OPTIONAL
						}	OPTIONAL
					}	OPTIONAL
				},		
				criticalExtensions				CHOICE {
					r6								SEQUENCE {
						cellUpdateConfirm-r6			CellUpdateConfirm-r6-IEs,
						cellUpdateConfirm-r6-add-ext	BIT STRING		OPTIONAL,
						v6b0NonCriticalExtensions		SEQUENCE {
							cellUpdateConfirm-v6b0ext		CellUpdateConfirm-v6b0ext-IEs,
							nonCriticalExtensions			SEQUENCE {}		OPTIONAL
						}	OPTIONAL
					},
					criticalExtensions				CHOICE {
						r7								SEQUENCE {
							cellUpdateConfirm-r7			CellUpdateConfirm-r7-IEs,
							cellUpdateConfirm-r7-add-ext	BIT STRING
										(CONTAINING CellUpdateConfirm-r7-add-ext-IEs)	OPTIONAL,
							v780NonCriticalExtensions		SEQUENCE {
								cellUpdateConfirm-v780ext		CellUpdateConfirm-v780ext-IEs,
								v860NonCriticalExtensions		SEQUENCE {
									cellUpdateConfirm-v860ext		CellUpdateConfirm-v860ext-IEs,
									nonCriticalExtensions			SEQUENCE {}		OPTIONAL
								}	OPTIONAL
							}	OPTIONAL
						},
						criticalExtensions				CHOICE {
							r8								SEQUENCE {
								cellUpdateConfirm-r8			CellUpdateConfirm-r8-IEs,
								cellUpdateConfirm-r8-add-ext	BIT STRING		OPTIONAL,
								v7d0NonCriticalExtensions		SEQUENCE {
									cellUpdateConfirm-v7d0ext		CellUpdateConfirm-v7d0ext-IEs,
									v890NonCriticalExtensions		SEQUENCE {
										cellUpdateConfirm-v890ext
															CellUpdateConfirm-v890ext-IEs,
										v8a0NonCriticalExtensions		SEQUENCE {
											cellUpdateConfirm-v8a0ext
																CellUpdateConfirm-v8a0ext-IEs,
											v7f0NonCriticalExtensions	SEQUENCE {
												cellUpdateConfirm-v7f0ext	
																CellUpdateConfirm-v7f0ext-IEs,
												v7g0NonCriticalExtensions	SEQUENCE {
													cellUpdateConfirm-v7g0ext
																	CellUpdateConfirm-v7g0ext-IEs,
													nonCriticalExtensions	SEQUENCE {}		OPTIONAL
												}	OPTIONAL
											}	OPTIONAL
										}	OPTIONAL
									}	OPTIONAL
								}	OPTIONAL
							},
							criticalExtensions				CHOICE {
								r9								SEQUENCE {
									cellUpdateConfirm-r9			CellUpdateConfirm-r9-IEs,
									-- Container for adding non critical extensions after 
									-- freezing REL-10
									cellUpdateConfirm-r9-add-ext	BIT STRING		OPTIONAL,
									nonCriticalExtensions			SEQUENCE {}		OPTIONAL
								},
								criticalExtensions				CHOICE {
									r10								SEQUENCE {
										cellUpdateConfirm-r10			CellUpdateConfirm-r10-IEs,
										-- Container for adding non critical extensions after 
										-- freezing REL-11
										cellUpdateConfirm-r10-add-ext	BIT STRING		OPTIONAL,
										vb50NonCriticalExtensions		SEQUENCE {
											cellUpdateConfirm-vb50ext
																CellUpdateConfirm-vb50ext-IEs,
											nonCriticalExtensions			SEQUENCE {}		OPTIONAL
										}	OPTIONAL
									},
									criticalExtensions				CHOICE {
										r11								SEQUENCE {
											cellUpdateConfirm-r11		CellUpdateConfirm-r11-IEs,
											-- Container for adding non critical extensions after 
											-- freezing REL-12
											cellUpdateConfirm-r11-add-ext	BIT STRING	OPTIONAL,
											nonCriticalExtensions			SEQUENCE {}		OPTIONAL
										},
										criticalExtensions				SEQUENCE {}
									}
								}
							}
						}
					}
				}
			}
		}
	}
}

-- ***************************************************
--
-- COUNTER CHECK
--
-- ***************************************************

CounterCheck ::= CHOICE {
	r3								SEQUENCE {
		counterCheck-r3					CounterCheck-r3-IEs,
		laterNonCriticalExtensions		SEQUENCE {
			-- Container for additional R99 extensions
			counterCheck-r3-add-ext		BIT STRING	OPTIONAL,
			nonCriticalExtensions		SEQUENCE {}	OPTIONAL
		}	OPTIONAL
	},
	later-than-r3					SEQUENCE {
		rrc-TransactionIdentifier		RRC-TransactionIdentifier,
		criticalExtensions				SEQUENCE {}
	}
}

CounterCheck-r3-IEs ::= SEQUENCE {
	-- User equipment IEs
		rrc-TransactionIdentifier		RRC-TransactionIdentifier,
	-- Radio bearer IEs
		rb-COUNT-C-MSB-InformationList	RB-COUNT-C-MSB-InformationList
}

-- ***************************************************
--
-- COUNTER CHECK RESPONSE
--
-- ***************************************************

CounterCheckResponse ::= SEQUENCE {
	-- User equipment IEs
		rrc-TransactionIdentifier		RRC-TransactionIdentifier,
	-- Radio bearer IEs
		rb-COUNT-C-InformationList		RB-COUNT-C-InformationList			OPTIONAL,
		laterNonCriticalExtensions		SEQUENCE {
			-- Container for additional R99 extensions
			counterCheckResponse-r3-add-ext		BIT STRING	OPTIONAL,
			nonCriticalExtensions				SEQUENCE {}	OPTIONAL
		}	OPTIONAL
}

-- ***************************************************
--
-- DOWNLINK DIRECT TRANSFER
--
-- ***************************************************

DownlinkDirectTransfer ::= CHOICE {
	r3								SEQUENCE {
		downlinkDirectTransfer-r3		DownlinkDirectTransfer-r3-IEs,
		laterNonCriticalExtensions		SEQUENCE {
			-- Container for additional R99 extensions
			downlinkDirectTransfer-r3-add-ext		BIT STRING	OPTIONAL,
			nonCriticalExtensions			SEQUENCE {}	OPTIONAL
		}	OPTIONAL
	},
	later-than-r3					SEQUENCE {
		rrc-TransactionIdentifier		RRC-TransactionIdentifier,
		criticalExtensions				SEQUENCE {}
	}
}

DownlinkDirectTransfer-r3-IEs ::= SEQUENCE {
	-- User equipment IEs
		rrc-TransactionIdentifier		RRC-TransactionIdentifier,
	-- Core network IEs
		cn-DomainIdentity				CN-DomainIdentity,
		nas-Message						NAS-Message
}

-- ***************************************************
--
-- ETWS PRIMARY NOTIFICATION WITH SECURITY
--
-- ***************************************************

ETWSPrimaryNotificationWithSecurity ::= SEQUENCE {
	-- Other IEs
		etws-Information				ETWS-Information,
		-- dummy is not used in the specification. If received it is ignored by the UE.
		-- See TS 23.041 for handling of warning security information by Cell Broadcast Center.
		dummy							ETWS-WarningSecurityInfo			OPTIONAL,
	-- Non critical extensions
		nonCriticalExtensions			SEQUENCE {}		OPTIONAL
}

-- ***************************************************
--
-- HANDOVER TO UTRAN COMMAND
--
-- ***************************************************

HandoverToUTRANCommand ::= CHOICE {
	r3								SEQUENCE {
		handoverToUTRANCommand-r3		HandoverToUTRANCommand-r3-IEs,
		nonCriticalExtensions			SEQUENCE {} OPTIONAL
	},
	criticalExtensions				CHOICE {
		r4								SEQUENCE {
			handoverToUTRANCommand-r4		HandoverToUTRANCommand-r4-IEs,
			nonCriticalExtensions			SEQUENCE {}		OPTIONAL
		},
		criticalExtensions				CHOICE {
			r5								SEQUENCE {
				handoverToUTRANCommand-r5		HandoverToUTRANCommand-r5-IEs,
				nonCriticalExtensions			SEQUENCE {}		OPTIONAL
			},
			criticalExtensions				CHOICE {
				r6								SEQUENCE {
					handoverToUTRANCommand-r6		HandoverToUTRANCommand-r6-IEs,
					v6b0NonCriticalExtensions		SEQUENCE {
						handoverToUTRANCommand-v6b0ext	HandoverToUTRANCommand-v6b0ext-IEs,
						nonCriticalExtensions			SEQUENCE {}		OPTIONAL
					}	OPTIONAL
				},
				criticalExtensions				CHOICE {
					r7								SEQUENCE {
						handoverToUTRANCommand-r7		HandoverToUTRANCommand-r7-IEs,
						v780NonCriticalExtensions		SEQUENCE {
							handoverToUTRANCommand-v780ext	HandoverToUTRANCommand-v780ext-IEs,
							v820NonCriticalExtensions		SEQUENCE {
								handoverToUTRANCommand-v820ext	HandoverToUTRANCommand-v820ext-IEs,
								v7d0NonCriticalExtensions		SEQUENCE {
									handoverToUTRANCommand-v7d0ext
																HandoverToUTRANCommand-v7d0ext-IEs,
									nonCriticalExtensions			SEQUENCE {}		OPTIONAL
								}	OPTIONAL
							}	OPTIONAL
						}	OPTIONAL
					},
					criticalExtensions				CHOICE {
						r8								SEQUENCE {
							handoverToUTRANCommand-r8		HandoverToUTRANCommand-r8-IEs,
							v7d0NonCriticalExtensions		SEQUENCE {
								handoverToUTRANCommand-v7d0ext	HandoverToUTRANCommand-v7d0ext-IEs,
								v890NonCriticalExtensions		SEQUENCE {
									handoverToUTRANCommand-v890ext
															HandoverToUTRANCommand-v890ext-IEs,
									v8a0NonCriticalExtensions		SEQUENCE {
										handoverToUTRANCommand-v8a0ext
																HandoverToUTRANCommand-v8a0ext-IEs,
										nonCriticalExtensions			SEQUENCE {}		OPTIONAL
									}	OPTIONAL
								}	OPTIONAL
							}	OPTIONAL
						},
						criticalExtensions				CHOICE {
							r9								SEQUENCE {
								handoverToUTRANCommand-r9		HandoverToUTRANCommand-r9-IEs,
								v9c0NonCriticalExtensions		SEQUENCE {
									handoverToUTRANCommand-v9c0ext
														HandoverToUTRANCommand-v9c0ext-IEs,
									nonCriticalExtensions			SEQUENCE {}		OPTIONAL
								}	OPTIONAL
							},
							criticalExtensions				HandoverToUTRANCommand-LaterCriticalExtensions
						}
					}
				}
			}
		}
	}
}


HandoverToUTRANCommand-r3-IEs ::= SEQUENCE {
	-- User equipment IEs
		new-U-RNTI						U-RNTI-Short,
		-- dummy is not used in this version of specification, it should
		-- not be sent and if received it should be ignored.
		dummy							ActivationTime						OPTIONAL,
		cipheringAlgorithm				CipheringAlgorithm					OPTIONAL,
	-- Radio bearer IEs
	-- Specification mode information
		specificationMode				CHOICE {
			complete						SEQUENCE {
				srb-InformationSetupList		SRB-InformationSetupList,
				rab-InformationSetupList		RAB-InformationSetupList			OPTIONAL,
				ul-CommonTransChInfo			UL-CommonTransChInfo,
				ul-AddReconfTransChInfoList		UL-AddReconfTransChInfoList,
				dl-CommonTransChInfo			DL-CommonTransChInfo,
				dl-AddReconfTransChInfoList		DL-AddReconfTransChInfoList,
				ul-DPCH-Info					UL-DPCH-Info,
				modeSpecificInfo				CHOICE {
					fdd								SEQUENCE {
						-- dummy and dummy2 are not used in this version of specification,
						-- they should not be sent and if received they should be ignored.
						dummy							DL-PDSCH-Information OPTIONAL,
						dummy2							CPCH-SetInfo		OPTIONAL
					},
					tdd								NULL
				},
				dl-CommonInformation			DL-CommonInformation,
				dl-InformationPerRL-List		DL-InformationPerRL-List,
				frequencyInfo					FrequencyInfo
			},
			preconfiguration				SEQUENCE {
-- All IEs that include an FDD/TDD choice are split in two IEs for this message,
-- one for the FDD only elements and one for the TDD only elements, so that one
-- FDD/TDD choice in this level is sufficient.
				preConfigMode					CHOICE {
					predefinedConfigIdentity		PredefinedConfigIdentity,
					defaultConfig					SEQUENCE {
						defaultConfigMode				DefaultConfigMode,
						defaultConfigIdentity 			DefaultConfigIdentity
					}
				},
				rab-Info						RAB-Info-Post		OPTIONAL,
				modeSpecificInfo				CHOICE {
					fdd								SEQUENCE {
						ul-DPCH-Info					UL-DPCH-InfoPostFDD,
						dl-CommonInformationPost		DL-CommonInformationPost,
						dl-InformationPerRL-List		DL-InformationPerRL-ListPostFDD,
						frequencyInfo					FrequencyInfoFDD
					},
					tdd									SEQUENCE {
						ul-DPCH-Info					UL-DPCH-InfoPostTDD,
						dl-CommonInformationPost		DL-CommonInformationPost,
						dl-InformationPerRL				DL-InformationPerRL-PostTDD,
						frequencyInfo					FrequencyInfoTDD,
						primaryCCPCH-TX-Power			PrimaryCCPCH-TX-Power
					}
				}
			}
		},
	-- Physical channel IEs
		maxAllowedUL-TX-Power			MaxAllowedUL-TX-Power
}

HandoverToUTRANCommand-r4-IEs ::= SEQUENCE {
	-- User equipment IEs
		new-U-RNTI						U-RNTI-Short,
		cipheringAlgorithm				CipheringAlgorithm					OPTIONAL,
	-- Radio bearer IEs
	-- Specification mode information
		specificationMode				CHOICE {
			complete						SEQUENCE {
				srb-InformationSetupList		SRB-InformationSetupList,
				rab-InformationSetupList		RAB-InformationSetupList-r4			OPTIONAL,
				ul-CommonTransChInfo			UL-CommonTransChInfo-r4,
				ul-AddReconfTransChInfoList		UL-AddReconfTransChInfoList,
				dl-CommonTransChInfo			DL-CommonTransChInfo-r4,
				dl-AddReconfTransChInfoList		DL-AddReconfTransChInfoList-r4,
				ul-DPCH-Info					UL-DPCH-Info-r4,
				modeSpecificInfo				CHOICE {
					fdd								SEQUENCE {
						-- dummy and dummy2 are not used in this version of specification,
						-- they should not be sent and if received they should be ignored.
						dummy							DL-PDSCH-Information OPTIONAL,
						dummy2							CPCH-SetInfo		OPTIONAL
					},
					tdd								NULL
				},
				dl-CommonInformation			DL-CommonInformation-r4,
				dl-InformationPerRL-List		DL-InformationPerRL-List-r4,
				frequencyInfo					FrequencyInfo
			},
			preconfiguration				SEQUENCE {
-- All IEs that include an FDD/TDD choice are split in two IEs for this message,
-- one for the FDD only elements and one for the TDD only elements, so that one
-- FDD/TDD choice in this level is sufficient.
				preConfigMode					CHOICE {
					predefinedConfigIdentity		PredefinedConfigIdentity,
					defaultConfig					SEQUENCE {
						defaultConfigMode				DefaultConfigMode,
						defaultConfigIdentity 			DefaultConfigIdentity-r4
					}
				},
				rab-Info						RAB-Info-Post		OPTIONAL,
				modeSpecificInfo				CHOICE {
					fdd								SEQUENCE {
						ul-DPCH-Info					UL-DPCH-InfoPostFDD,
						dl-CommonInformationPost		DL-CommonInformationPost,
						dl-InformationPerRL-List		DL-InformationPerRL-ListPostFDD,
						frequencyInfo					FrequencyInfoFDD
					},
					tdd								CHOICE {
						tdd384							SEQUENCE {
							ul-DPCH-Info					UL-DPCH-InfoPostTDD,
							dl-InformationPerRL				DL-InformationPerRL-PostTDD,
							frequencyInfo					FrequencyInfoTDD,
							primaryCCPCH-TX-Power			PrimaryCCPCH-TX-Power
						},
						tdd128							SEQUENCE {
							ul-DPCH-Info					UL-DPCH-InfoPostTDD-LCR-r4,
							dl-InformationPerRL				DL-InformationPerRL-PostTDD-LCR-r4,
							frequencyInfo					FrequencyInfoTDD,
							primaryCCPCH-TX-Power			PrimaryCCPCH-TX-Power
						}
					}
				}
			}
		},
	-- Physical channel IEs
		maxAllowedUL-TX-Power			MaxAllowedUL-TX-Power
}

HandoverToUTRANCommand-r5-IEs ::= SEQUENCE {
	-- User equipment IEs
		new-U-RNTI						U-RNTI-Short,
		cipheringAlgorithm				CipheringAlgorithm					OPTIONAL,
	-- Radio bearer IEs
	-- Specification mode information
		specificationMode				CHOICE {
			complete						SEQUENCE {
				srb-InformationSetupList		SRB-InformationSetupList-r5,
				rab-InformationSetupList		RAB-InformationSetupList-r5			OPTIONAL,
				ul-CommonTransChInfo			UL-CommonTransChInfo-r4,
				ul-AddReconfTransChInfoList		UL-AddReconfTransChInfoList,
				dl-CommonTransChInfo			DL-CommonTransChInfo-r4,
				dl-AddReconfTransChInfoList		DL-AddReconfTransChInfoList-r5,
				ul-DPCH-Info					UL-DPCH-Info-r5,
				modeSpecificInfo				CHOICE {
					fdd								SEQUENCE {
						-- dummy and dummy2 are not used in this version of specification,
						-- they should not be sent and if received they should be ignored.
						dummy							DL-PDSCH-Information OPTIONAL,
						dummy2							CPCH-SetInfo		OPTIONAL
					},
					tdd								NULL
				},
				dl-CommonInformation			DL-CommonInformation-r4,
				dl-InformationPerRL-List		DL-InformationPerRL-List-r5,
				frequencyInfo					FrequencyInfo
			},
			preconfiguration				SEQUENCE {
-- All IEs that include an FDD/TDD choice are split in two IEs for this message,
-- one for the FDD only elements and one for the TDD only elements, so that one
-- FDD/TDD choice in this level is sufficient.
				preConfigMode					CHOICE {
					predefinedConfigIdentity		PredefinedConfigIdentity,
					defaultConfig					SEQUENCE {
						defaultConfigMode				DefaultConfigMode,
						defaultConfigIdentity 			DefaultConfigIdentity-r5
					}
				},
				rab-Info						RAB-Info-Post		OPTIONAL,
				modeSpecificInfo				CHOICE {
					fdd								SEQUENCE {
						ul-DPCH-Info					UL-DPCH-InfoPostFDD,
						dl-CommonInformationPost		DL-CommonInformationPost,
						dl-InformationPerRL-List		DL-InformationPerRL-ListPostFDD,
						frequencyInfo					FrequencyInfoFDD
					},
					tdd								CHOICE {
						tdd384							SEQUENCE {
							ul-DPCH-Info					UL-DPCH-InfoPostTDD,
							dl-InformationPerRL				DL-InformationPerRL-PostTDD,
							frequencyInfo					FrequencyInfoTDD,
							primaryCCPCH-TX-Power			PrimaryCCPCH-TX-Power
						},
						tdd128							SEQUENCE {
							ul-DPCH-Info					UL-DPCH-InfoPostTDD-LCR-r4,
							dl-InformationPerRL				DL-InformationPerRL-PostTDD-LCR-r4,
							frequencyInfo					FrequencyInfoTDD,
							primaryCCPCH-TX-Power			PrimaryCCPCH-TX-Power
						}
					}
				}
			}
		},
	-- Physical channel IEs
		maxAllowedUL-TX-Power			MaxAllowedUL-TX-Power
}

HandoverToUTRANCommand-r6-IEs ::= SEQUENCE {
	-- User equipment IEs
		new-U-RNTI						U-RNTI-Short,
		cipheringAlgorithm				CipheringAlgorithm					OPTIONAL,
	-- Radio bearer IEs
	-- Specification mode information
		specificationMode				CHOICE {
			complete						SEQUENCE {
				srb-InformationSetupList		SRB-InformationSetupList-r6,
				rab-InformationSetupList		RAB-InformationSetupList-r6		OPTIONAL,
				ul-CommonTransChInfo			UL-CommonTransChInfo-r4,
				ul-AddReconfTransChInfoList		UL-AddReconfTransChInfoList-r6,
				dl-CommonTransChInfo			DL-CommonTransChInfo-r4,
				dl-AddReconfTransChInfoList		DL-AddReconfTransChInfoList-r5,
				ul-DPCH-Info					UL-DPCH-Info-r6,
				ul-EDCH-Information				UL-EDCH-Information-r6			OPTIONAL,
				dl-HSPDSCH-Information			DL-HSPDSCH-Information-r6		OPTIONAL,
				dl-CommonInformation			DL-CommonInformation-r6,
				dl-InformationPerRL-List		DL-InformationPerRL-List-r6,
				frequencyInfo					FrequencyInfo
			},
			preconfiguration				SEQUENCE {
				-- All IEs that include an FDD/TDD choice are split in two IEs for this message,
				-- one for the FDD only elements and one for the TDD only elements, so that one
				-- FDD/TDD choice in this level is sufficient.
				preConfigMode					CHOICE {
					predefinedConfigIdentity		PredefinedConfigIdentity,
					defaultConfig					SEQUENCE {
						defaultConfigMode				DefaultConfigMode,
						defaultConfigIdentity 			DefaultConfigIdentity-r6
					}
				},
				rab-Info						RAB-Info-Post		OPTIONAL,
				modeSpecificInfo				CHOICE {
					fdd								SEQUENCE {
						ul-DPCH-Info					UL-DPCH-InfoPostFDD,
						dl-CommonInformationPost		DL-CommonInformationPost,
						dl-InformationPerRL-List		DL-InformationPerRL-ListPostFDD,
						frequencyInfo					FrequencyInfoFDD
					},
					tdd								CHOICE {
						tdd384							SEQUENCE {
							ul-DPCH-Info					UL-DPCH-InfoPostTDD,
							dl-InformationPerRL				DL-InformationPerRL-PostTDD,
							frequencyInfo					FrequencyInfoTDD,
							primaryCCPCH-TX-Power			PrimaryCCPCH-TX-Power
						},
						tdd128							SEQUENCE {
							ul-DPCH-Info					UL-DPCH-InfoPostTDD-LCR-r4,
							dl-InformationPerRL				DL-InformationPerRL-PostTDD-LCR-r4,
							frequencyInfo					FrequencyInfoTDD,
							primaryCCPCH-TX-Power			PrimaryCCPCH-TX-Power
						}
					}
				}
			}
		},
	-- Physical channel IEs
		maxAllowedUL-TX-Power			MaxAllowedUL-TX-Power
}

HandoverToUTRANCommand-v6b0ext-IEs ::= SEQUENCE {
	ue-hspa-identities						UE-HSPA-Identities-r6	OPTIONAL
}

HandoverToUTRANCommand-r7-IEs ::= SEQUENCE {
	-- User equipment IEs
		new-U-RNTI						U-RNTI-Short,
		cipheringAlgorithm				CipheringAlgorithm-r7					OPTIONAL,
		supportForChangeOfUE-Capability	BOOLEAN,
		new-H-RNTI						H-RNTI									OPTIONAL,
		newPrimary-E-RNTI				E-RNTI									OPTIONAL,
		newSecondary-E-RNTI				E-RNTI									OPTIONAL,
	-- Radio bearer IEs
	-- Specification mode information
		specificationMode				CHOICE {
			complete						SEQUENCE {
				srb-InformationSetupList		SRB-InformationSetupList-r7,
				rab-InformationSetupList		RAB-InformationSetupList-r7		OPTIONAL,
				ul-CommonTransChInfo			UL-CommonTransChInfo-r4,
				ul-AddReconfTransChInfoList		UL-AddReconfTransChInfoList-r7,
				dl-CommonTransChInfo			DL-CommonTransChInfo-r4,
				dl-AddReconfTransChInfoList		DL-AddReconfTransChInfoList-r7,
				ul-DPCH-Info					UL-DPCH-Info-r7,
				ul-EDCH-Information				UL-EDCH-Information-r7			OPTIONAL,
				dl-HSPDSCH-Information			DL-HSPDSCH-Information-r7		OPTIONAL,
				dl-CommonInformation			DL-CommonInformation-r7,
				dl-InformationPerRL-List		DL-InformationPerRL-List-r7,
				frequencyInfo					FrequencyInfo,
				multi-frequencyInfo				Multi-frequencyInfo-LCR-r7		OPTIONAL
			},
			preconfiguration				SEQUENCE {
				-- All IEs that include an FDD/TDD choice are split in two IEs for this message,
				-- one for the FDD only elements and one for the TDD only elements, so that one
				-- FDD/TDD choice in this level is sufficient.
				preConfigMode					CHOICE {
					predefinedConfigIdentity		PredefinedConfigIdentity,
					defaultConfig					SEQUENCE {
						defaultConfigMode				DefaultConfigMode,
						defaultConfigIdentity 			DefaultConfigIdentity-r6
					}
				},
				rab-Info						RAB-Info-Post		OPTIONAL,
				modeSpecificInfo				CHOICE {
					fdd								SEQUENCE {
						ul-DPCH-Info					UL-DPCH-InfoPostFDD,
						dl-CommonInformationPost		DL-CommonInformationPost,
						dl-InformationPerRL-List		DL-InformationPerRL-ListPostFDD,
						frequencyInfo					FrequencyInfoFDD
					},
					tdd								CHOICE {
						tdd384							SEQUENCE {
							ul-DPCH-Info					UL-DPCH-InfoPostTDD,
							dl-InformationPerRL				DL-InformationPerRL-PostTDD,
							frequencyInfo					FrequencyInfoTDD,
							primaryCCPCH-TX-Power			PrimaryCCPCH-TX-Power
						},
						tdd128							SEQUENCE {
							ul-DPCH-Info					UL-DPCH-Info-r7,
							dl-InformationPerRL				DL-InformationPerRL-PostTDD-LCR-r4,
							frequencyInfo					FrequencyInfoTDD,
							primaryCCPCH-TX-Power			PrimaryCCPCH-TX-Power,
							multi-frequencyInfo				Multi-frequencyInfo-LCR-r7		OPTIONAL
						},
						tdd768							SEQUENCE {
							ul-DPCH-Info					UL-DPCH-Info-r7,
							dl-InformationPerRL				DL-InformationPerRL-List-r7,
							frequencyInfo					FrequencyInfoTDD,
							primaryCCPCH-TX-Power			PrimaryCCPCH-TX-Power
						}
					}
				}
			}
		},
	-- Physical channel IEs
		maxAllowedUL-TX-Power			MaxAllowedUL-TX-Power
}

HandoverToUTRANCommand-v780ext-IEs ::= SEQUENCE {
	-- Physical channel IEs
		hs-DSCH-TBSizeTable				HS-DSCH-TBSizeTable						OPTIONAL
}

HandoverToUTRANCommand-v7d0ext-IEs ::= SEQUENCE {
	-- Physical channel IEs
		ul-EDCH-Information				UL-EDCH-Information-ext				OPTIONAL
}

HandoverToUTRANCommand-r8-IEs ::= SEQUENCE {
	-- User equipment IEs
		new-U-RNTI						U-RNTI-Short,
		cipheringAlgorithm				CipheringAlgorithm-r7					OPTIONAL,
		supportForChangeOfUE-Capability	BOOLEAN,
		new-H-RNTI						H-RNTI									OPTIONAL,
		newPrimary-E-RNTI				E-RNTI									OPTIONAL,
		newSecondary-E-RNTI				E-RNTI									OPTIONAL,
	-- Radio bearer IEs
	-- Specification mode information
		-- dummy is not used in this version of the specification, it should
		-- not be sent and if received it should be ignored.
		dummy							DefaultConfigForCellFACH				OPTIONAL,
		specificationMode				CHOICE {
			complete						SEQUENCE {
				srb-InformationSetupList		SRB-InformationSetupList-r8,
				rab-InformationSetupList		RAB-InformationSetupList-r8		OPTIONAL,
				ul-CommonTransChInfo			UL-CommonTransChInfo-r4,
				ul-AddReconfTransChInfoList		UL-AddReconfTransChInfoList-r8,
				dl-CommonTransChInfo			DL-CommonTransChInfo-r4,
				dl-AddReconfTransChInfoList		DL-AddReconfTransChInfoList-r7,
				ul-DPCH-Info					UL-DPCH-Info-r7,
				ul-EDCH-Information				UL-EDCH-Information-r8			OPTIONAL,
				dl-HSPDSCH-Information			DL-HSPDSCH-Information-r8		OPTIONAL,
				dl-CommonInformation			DL-CommonInformation-r8,
				dl-InformationPerRL-List		DL-InformationPerRL-List-r7,
				frequencyInfo					FrequencyInfo,
				multi-frequencyInfo				Multi-frequencyInfo-LCR-r7		OPTIONAL
			},
			preconfiguration				SEQUENCE {
				-- All IEs that include an FDD/TDD choice are split in two IEs for this message,
				-- one for the FDD only elements and one for the TDD only elements, so that one
				-- FDD/TDD choice in this level is sufficient.
				preConfigMode					CHOICE {
					predefinedConfigIdentity		PredefinedConfigIdentity,
					defaultConfig					SEQUENCE {
						defaultConfigMode				DefaultConfigMode,
						defaultConfigIdentity			DefaultConfigIdentity-r6,
						-- dummy is not used in this version of the specification, it should
						-- not be sent and if received it should be ignored
						dummy			DLUL-HSPA-Information-r8	OPTIONAL
					}
				},
				rab-Info						RAB-Info-Post		OPTIONAL,
				modeSpecificInfo				CHOICE {
					fdd								SEQUENCE {
						ul-DPCH-Info					UL-DPCH-InfoPostFDD,
						dl-CommonInformationPost		DL-CommonInformationPost,
						dl-InformationPerRL-List		DL-InformationPerRL-ListPostFDD,
						frequencyInfo					FrequencyInfoFDD
					},
					tdd								CHOICE {
						tdd384							SEQUENCE {
							ul-DPCH-Info					UL-DPCH-InfoPostTDD,
							dl-InformationPerRL				DL-InformationPerRL-PostTDD,
							frequencyInfo					FrequencyInfoTDD,
							primaryCCPCH-TX-Power			PrimaryCCPCH-TX-Power
						},
						tdd128							SEQUENCE {
							ul-DPCH-Info					UL-DPCH-Info-r7,
							dl-InformationPerRL				DL-InformationPerRL-PostTDD-LCR-r4,
							frequencyInfo					FrequencyInfoTDD,
							primaryCCPCH-TX-Power			PrimaryCCPCH-TX-Power,
							multi-frequencyInfo				Multi-frequencyInfo-LCR-r7		OPTIONAL
						},
						tdd768							SEQUENCE {
							ul-DPCH-Info					UL-DPCH-Info-r7,
							dl-InformationPerRL				DL-InformationPerRL-List-r7,
							frequencyInfo					FrequencyInfoTDD,
							primaryCCPCH-TX-Power			PrimaryCCPCH-TX-Power
						}
					}
				}
			}
		},
	-- Physical channel IEs
		maxAllowedUL-TX-Power			MaxAllowedUL-TX-Power
}

HandoverToUTRANCommand-v820ext-IEs ::= SEQUENCE {
	-- Radio bearer IEs
		rab-InformationSetupList		RAB-InformationSetupList-v820ext		OPTIONAL
}

HandoverToUTRANCommand-v890ext-IEs ::= SEQUENCE {
	-- Physical channel IEs
		dl-HSPDSCH-Information			DL-HSPDSCH-Information-r8-ext		OPTIONAL
}

HandoverToUTRANCommand-v8a0ext-IEs ::= SEQUENCE {
	-- Physical channel IEs
		dl-HSPDSCH-Information			DL-HSPDSCH-Information-r8-ext2		OPTIONAL
}

HandoverToUTRANCommand-r9-IEs ::= SEQUENCE {
	-- User equipment IEs
		new-U-RNTI						U-RNTI-Short,
		cipheringAlgorithm				CipheringAlgorithm-r7					OPTIONAL,
		supportForChangeOfUE-Capability	BOOLEAN,
		new-H-RNTI						H-RNTI									OPTIONAL,
		newPrimary-E-RNTI				E-RNTI									OPTIONAL,
		newSecondary-E-RNTI				E-RNTI									OPTIONAL,
	-- Radio bearer IEs
	-- Specification mode information
		defaultConfigForCellFACH		DefaultConfigForCellFACH				OPTIONAL,
		specificationMode				CHOICE {
			complete						SEQUENCE {
				srb-InformationSetupList		SRB-InformationSetupList-r8,
				rab-InformationSetupList		RAB-InformationSetupList-r8		OPTIONAL,
				ul-CommonTransChInfo			UL-CommonTransChInfo-r4,
				ul-AddReconfTransChInfoList		UL-AddReconfTransChInfoList-r8,
				dl-CommonTransChInfo			DL-CommonTransChInfo-r4,
				dl-AddReconfTransChInfoList		DL-AddReconfTransChInfoList-r9,
				ul-DPCH-Info					UL-DPCH-Info-r7,
				ul-EDCH-Information				UL-EDCH-Information-r9			OPTIONAL,
				dl-HSPDSCH-Information			DL-HSPDSCH-Information-r9		OPTIONAL,
				dl-CommonInformation			DL-CommonInformation-r8,
				dl-InformationPerRL-List		DL-InformationPerRL-List-r7,
				frequencyInfo					FrequencyInfo,
				multi-frequencyInfo				Multi-frequencyInfo-LCR-r7		OPTIONAL
			},
			preconfiguration				SEQUENCE {
				-- All IEs that include an FDD/TDD choice are split in two IEs for this message,
				-- one for the FDD only elements and one for the TDD only elements, so that one
				-- FDD/TDD choice in this level is sufficient.
				preConfigMode					CHOICE {
					predefinedConfigIdentity		PredefinedConfigIdentity,
					defaultConfig					SEQUENCE {
						defaultConfigMode				DefaultConfigMode,
						defaultConfigIdentity			DefaultConfigIdentity-r6,
						-- dummy is not used in this version of the specification, it should
						-- not be sent and if received it should be ignored
						dummy			DLUL-HSPA-Information-r9	OPTIONAL
					}
				},
				rab-Info						RAB-Info-Post		OPTIONAL,
				modeSpecificInfo				CHOICE {
					fdd								SEQUENCE {
						ul-DPCH-Info					UL-DPCH-InfoPostFDD,
						dl-CommonInformationPost		DL-CommonInformationPost,
						dl-InformationPerRL-List		DL-InformationPerRL-ListPostFDD,
						frequencyInfo					FrequencyInfoFDD
					},
					tdd								CHOICE {
						tdd384							SEQUENCE {
							ul-DPCH-Info					UL-DPCH-InfoPostTDD,
							dl-InformationPerRL				DL-InformationPerRL-PostTDD,
							frequencyInfo					FrequencyInfoTDD,
							primaryCCPCH-TX-Power			PrimaryCCPCH-TX-Power
						},
						tdd128							SEQUENCE {
							ul-DPCH-Info					UL-DPCH-Info-r7,
							dl-InformationPerRL				DL-InformationPerRL-PostTDD-LCR-r4,
							frequencyInfo					FrequencyInfoTDD,
							primaryCCPCH-TX-Power			PrimaryCCPCH-TX-Power,
							multi-frequencyInfo				Multi-frequencyInfo-LCR-r7		OPTIONAL
						},
						tdd768							SEQUENCE {
							ul-DPCH-Info					UL-DPCH-Info-r7,
							dl-InformationPerRL				DL-InformationPerRL-List-r7,
							frequencyInfo					FrequencyInfoTDD,
							primaryCCPCH-TX-Power			PrimaryCCPCH-TX-Power
						}
					}
				}
			}
		},
	-- Physical channel IEs
		maxAllowedUL-TX-Power			MaxAllowedUL-TX-Power
}

HandoverToUTRANCommand-v9c0ext-IEs ::= SEQUENCE {
	-- For 1.28Mcps TDD only
		dl-AddReconfTransChInfoList		DL-AddReconfTransChInfoList-TDD128-v9c0ext			OPTIONAL
}

HandoverToUTRANCommand-LaterCriticalExtensions ::= CHOICE {
		r10							SEQUENCE {
			handoverToUTRANCommand-r10		HandoverToUTRANCommand-r10-IEs,
			v9c0NonCriticalExtensions		SEQUENCE {
				handoverToUTRANCommand-v9c0ext
								HandoverToUTRANCommand-v9c0ext-IEs,
				nonCriticalExtensions			SEQUENCE {}		OPTIONAL
			}	OPTIONAL
		},
		criticalExtensions				CHOICE {
			r11								SEQUENCE {
				handoverToUTRANCommand-r11		HandoverToUTRANCommand-r11-IEs,
				-- Container for adding non critical extensions after freezing REL-12
				handoverToUTRANCommand-r11-add-ext	BIT STRING		OPTIONAL,
				nonCriticalExtensions				SEQUENCE {}		OPTIONAL
			},
			criticalExtensions				SEQUENCE {}
		}
}

HandoverToUTRANCommand-r10-IEs ::= SEQUENCE {
	-- User equipment IEs
		new-U-RNTI						U-RNTI-Short,
		cipheringAlgorithm				CipheringAlgorithm-r7					OPTIONAL,
		supportForChangeOfUE-Capability	BOOLEAN,
		new-H-RNTI						H-RNTI									OPTIONAL,
		newPrimary-E-RNTI				E-RNTI									OPTIONAL,
		newSecondary-E-RNTI				E-RNTI									OPTIONAL,
	-- Radio bearer IEs
	-- Specification mode information
		defaultConfigForCellFACH		DefaultConfigForCellFACH				OPTIONAL,
		specificationMode				CHOICE {
			complete						SEQUENCE {
				srb-InformationSetupList		SRB-InformationSetupList-r8,
				rab-InformationSetupList		RAB-InformationSetupList-r8		OPTIONAL,
				ul-CommonTransChInfo			UL-CommonTransChInfo-r4,
				ul-AddReconfTransChInfoList		UL-AddReconfTransChInfoList-r8,
				dl-CommonTransChInfo			DL-CommonTransChInfo-r4,
				dl-AddReconfTransChInfoList		DL-AddReconfTransChInfoList-r9,
				ul-DPCH-Info					UL-DPCH-Info-r7,
				ul-EDCH-Information				UL-EDCH-Information-r9			OPTIONAL,
				dl-HSPDSCH-Information			DL-HSPDSCH-Information-r9		OPTIONAL,
				dl-CommonInformation			DL-CommonInformation-r10,
				dl-InformationPerRL-List		DL-InformationPerRL-List-r7,
				frequencyInfo					FrequencyInfo,
				multi-frequencyInfo				Multi-frequencyInfo-LCR-r7		OPTIONAL
			},
			preconfiguration				SEQUENCE {
				-- All IEs that include an FDD/TDD choice are split in two IEs for this message,
				-- one for the FDD only elements and one for the TDD only elements, so that one
				-- FDD/TDD choice in this level is sufficient.
				preConfigMode					CHOICE {
					predefinedConfigIdentity		PredefinedConfigIdentity,
					defaultConfig					SEQUENCE {
						defaultConfigMode				DefaultConfigMode,
						defaultConfigIdentity			DefaultConfigIdentity-r6,
						-- dummy is not used in this version of the specification, it should
						-- not be sent and if received it should be ignored
						dummy			DLUL-HSPA-Information-r10	OPTIONAL
					}
				},
				rab-Info						RAB-Info-Post		OPTIONAL,
				modeSpecificInfo				CHOICE {
					fdd								SEQUENCE {
						ul-DPCH-Info					UL-DPCH-InfoPostFDD,
						dl-CommonInformationPost		DL-CommonInformationPost,
						dl-InformationPerRL-List		DL-InformationPerRL-ListPostFDD,
						frequencyInfo					FrequencyInfoFDD
					},
					tdd								CHOICE {
						tdd384							SEQUENCE {
							ul-DPCH-Info					UL-DPCH-InfoPostTDD,
							dl-InformationPerRL				DL-InformationPerRL-PostTDD,
							frequencyInfo					FrequencyInfoTDD,
							primaryCCPCH-TX-Power			PrimaryCCPCH-TX-Power
						},
						tdd128							SEQUENCE {
							ul-DPCH-Info					UL-DPCH-Info-r7,
							dl-InformationPerRL				DL-InformationPerRL-PostTDD-LCR-r4,
							frequencyInfo					FrequencyInfoTDD,
							primaryCCPCH-TX-Power			PrimaryCCPCH-TX-Power,
							multi-frequencyInfo				Multi-frequencyInfo-LCR-r7		OPTIONAL
						},
						tdd768							SEQUENCE {
							ul-DPCH-Info					UL-DPCH-Info-r7,
							dl-InformationPerRL				DL-InformationPerRL-List-r7,
							frequencyInfo					FrequencyInfoTDD,
							primaryCCPCH-TX-Power			PrimaryCCPCH-TX-Power
						}
					}
				}
			}
		},
	-- Physical channel IEs
		maxAllowedUL-TX-Power			MaxAllowedUL-TX-Power
}

HandoverToUTRANCommand-r11-IEs ::= SEQUENCE {
	-- User equipment IEs
		new-U-RNTI						U-RNTI-Short,
		cipheringAlgorithm				CipheringAlgorithm-r7					OPTIONAL,
		supportForChangeOfUE-Capability	BOOLEAN,
		new-H-RNTI						H-RNTI									OPTIONAL,
		newPrimary-E-RNTI				E-RNTI									OPTIONAL,
		newSecondary-E-RNTI				E-RNTI									OPTIONAL,
	-- Radio bearer IEs
	-- Specification mode information
		defaultConfigForCellFACH		DefaultConfigForCellFACH				OPTIONAL,
		specificationMode				CHOICE {
			complete						SEQUENCE {
				srb-InformationSetupList		SRB-InformationSetupList-r8,
				rab-InformationSetupList		RAB-InformationSetupList-r8		OPTIONAL,
				ul-CommonTransChInfo			UL-CommonTransChInfo-r4,
				ul-AddReconfTransChInfoList		UL-AddReconfTransChInfoList-r8,
				dl-CommonTransChInfo			DL-CommonTransChInfo-r4,
				dl-AddReconfTransChInfoList		DL-AddReconfTransChInfoList-r11,
				ul-DPCH-Info					UL-DPCH-Info-r11,
				ul-EDCH-Information				UL-EDCH-Information-r11			OPTIONAL,
				dl-HSPDSCH-Information			DL-HSPDSCH-Information-r11		OPTIONAL,
				dl-CommonInformation			DL-CommonInformation-r10,
				dl-InformationPerRL-List		DL-InformationPerRL-List-r11,
				frequencyInfo					FrequencyInfo,
				multi-frequencyInfo				Multi-frequencyInfo-LCR-r7		OPTIONAL
			},
			preconfiguration				SEQUENCE {
				-- All IEs that include an FDD/TDD choice are split in two IEs for this message,
				-- one for the FDD only elements and one for the TDD only elements, so that one
				-- FDD/TDD choice in this level is sufficient.
				preConfigMode					CHOICE {
					predefinedConfigIdentity		PredefinedConfigIdentity,
					defaultConfig					SEQUENCE {
						defaultConfigMode				DefaultConfigMode,
						defaultConfigIdentity			DefaultConfigIdentity-r6
					}
				},
				rab-Info						RAB-Info-Post		OPTIONAL,
				modeSpecificInfo				CHOICE {
					fdd								SEQUENCE {
						ul-DPCH-Info					UL-DPCH-InfoPostFDD,
						dl-CommonInformationPost		DL-CommonInformationPost,
						dl-InformationPerRL-List		DL-InformationPerRL-ListPostFDD,
						frequencyInfo					FrequencyInfoFDD
					},
					tdd								CHOICE {
						tdd384							SEQUENCE {
							ul-DPCH-Info					UL-DPCH-InfoPostTDD,
							dl-InformationPerRL				DL-InformationPerRL-PostTDD,
							frequencyInfo					FrequencyInfoTDD,
							primaryCCPCH-TX-Power			PrimaryCCPCH-TX-Power
						},
						tdd128							SEQUENCE {
							ul-DPCH-Info					UL-DPCH-Info-r7,
							dl-InformationPerRL				DL-InformationPerRL-PostTDD-LCR-r4,
							frequencyInfo					FrequencyInfoTDD,
							primaryCCPCH-TX-Power			PrimaryCCPCH-TX-Power,
							multi-frequencyInfo				Multi-frequencyInfo-LCR-r7		OPTIONAL
						},
						tdd768							SEQUENCE {
							ul-DPCH-Info					UL-DPCH-Info-r7,
							dl-InformationPerRL				DL-InformationPerRL-List-r7,
							frequencyInfo					FrequencyInfoTDD,
							primaryCCPCH-TX-Power			PrimaryCCPCH-TX-Power
						}
					}
				}
			}
		},
	-- Physical channel IEs
		maxAllowedUL-TX-Power			MaxAllowedUL-TX-Power
}

-- ***************************************************
--
-- HANDOVER TO UTRAN COMPLETE
--
-- ***************************************************

HandoverToUTRANComplete ::= SEQUENCE {
	--TABULAR: Integrity protection shall not be performed on this message.
	-- User equipment IEs
	-- TABULAR: startList is conditional on history.
		startList						STARTList							OPTIONAL,
	-- Radio bearer IEs
		count-C-ActivationTime			ActivationTime						OPTIONAL,
		laterNonCriticalExtensions		SEQUENCE {
			-- Container for additional R99 extensions
			handoverToUTRANComplete-r3-add-ext		BIT STRING	OPTIONAL,
			va40NonCriticalExtensions			SEQUENCE {
				handoverToUTRANComplete-va40ext	HandoverToUTRANComplete-va40ext,
				vb50NonCriticalExtensions			SEQUENCE {
					handoverToUTRANComplete-vb50ext	HandoverToUTRANComplete-vb50ext-IEs,
					nonCriticalExtensions			SEQUENCE {}		OPTIONAL
				}	OPTIONAL
			}	OPTIONAL
		}	OPTIONAL
}

HandoverToUTRANComplete-va40ext ::= SEQUENCE {
	loggedMeasAvailable				ENUMERATED { true }	OPTIONAL
}

HandoverToUTRANComplete-vb50ext-IEs ::= SEQUENCE {
	connEstFailInfoAvailable		ENUMERATED { true }	OPTIONAL
}

-- ***************************************************
--
-- INITIAL DIRECT TRANSFER
--
-- ***************************************************

InitialDirectTransfer ::= SEQUENCE {
	-- Core network IEs
		cn-DomainIdentity				CN-DomainIdentity,
		intraDomainNasNodeSelector		IntraDomainNasNodeSelector,
		nas-Message						NAS-Message,
	-- Measurement IEs
		measuredResultsOnRACH			MeasuredResultsOnRACH				OPTIONAL,
		v3a0NonCriticalExtensions		SEQUENCE {
		initialDirectTransfer-v3a0ext	InitialDirectTransfer-v3a0ext,
		laterNonCriticalExtensions		SEQUENCE {
			-- Container for additional R99 extensions
			initialDirectTransfer-r3-add-ext		BIT STRING	
								(CONTAINING InitialDirectTransfer-r3-add-ext-IEs)	OPTIONAL,
				v590NonCriticalExtensions		SEQUENCE {
					initialDirectTransfer-v590ext	InitialDirectTransfer-v590ext,
					v690NonCriticalExtensions		SEQUENCE {
						initialDirectTransfer-v690ext	InitialDirectTransfer-v690ext-IEs,
						v770NonCriticalExtensions		SEQUENCE {
							initialDirectTransfer-v770ext	InitialDirectTransfer-v770ext-IEs,
							v860NonCriticalExtensions		SEQUENCE {
								initialDirectTransfer-v860ext	InitialDirectTransfer-v860ext-IEs,
								vb50NonCriticalExtensions		SEQUENCE {
									initialDirectTransfer-vb50ext	InitialDirectTransfer-vb50ext-IEs,
									nonCriticalExtensions			SEQUENCE {}		OPTIONAL
								}		OPTIONAL
							}		OPTIONAL
						}		OPTIONAL
					}		OPTIONAL
				}		OPTIONAL
			}		OPTIONAL
		}	OPTIONAL
}

InitialDirectTransfer-v3a0ext ::= SEQUENCE {
	-- start-value shall always be included in this version of the protocol
	start-Value						START-Value							OPTIONAL
}
InitialDirectTransfer-v590ext ::= SEQUENCE {
	establishmentCause		EstablishmentCause	OPTIONAL
}

InitialDirectTransfer-v690ext-IEs ::= SEQUENCE {
	-- Core network IEs
		plmn-Identity					PLMN-Identity						OPTIONAL,
	-- Measurement IEs
		measuredResultsOnRACHinterFreq	MeasuredResultsOnRACHinterFreq		OPTIONAL,
	-- MBMS IEs
		mbms-JoinedInformation			MBMS-JoinedInformation-r6			OPTIONAL
}

InitialDirectTransfer-v770ext-IEs ::= SEQUENCE {
		csCallType						ENUMERATED { speech, video, other, spare }	OPTIONAL
}

InitialDirectTransfer-v860ext-IEs ::= SEQUENCE {
		supportOfCSG					ENUMERATED { true }					OPTIONAL
}

InitialDirectTransfer-r3-add-ext-IEs ::=		SEQUENCE {
	initialDirectTransfer-v7g0ext					InitialDirectTransfer-v7g0ext-IEs,
	nonCriticalExtensions				SEQUENCE {}		OPTIONAL
}

InitialDirectTransfer-v7g0ext-IEs ::=			SEQUENCE {
	-- Measurement IEs
	measuredResultsOnRACH-v7g0ext		MeasuredResultsOnRACH-v7g0ext		OPTIONAL
}

InitialDirectTransfer-vb50ext-IEs ::=	SEQUENCE {
	-- Measurement IEs
	measuredResultsOnRACHEUTRAFreq		MeasuredResultsOnRACH-EUTRAFreq		OPTIONAL
}

-- ***************************************************
--
-- HANDOVER FROM UTRAN COMMAND
--
-- ***************************************************

HandoverFromUTRANCommand-GSM ::= CHOICE {
	r3								SEQUENCE {
		handoverFromUTRANCommand-GSM-r3
										HandoverFromUTRANCommand-GSM-r3-IEs,
		-- UTRAN should not include the IE laterNonCriticalExtensions when it sets the IE 
		-- gsm-message included in handoverFromUTRANCommand-GSM-r3 to single-GSM-Message. The UE
		-- behaviour upon receiving a message with this combination of IE values is unspecified.
		laterNonCriticalExtensions		SEQUENCE {
			-- Container for additional R99 extensions
			handoverFromUTRANCommand-GSM-r3-add-ext		BIT STRING	OPTIONAL,
			-- UTRAN may apply the r3 version of the message to perform PS handover
			-- for a single RAB only
			v690NonCriticalExtensions		SEQUENCE {
				handoverFromUTRANCommand-GSM-v690ext	HandoverFromUTRANCommand-GSM-v690ext-IEs,
				v860NonCriticalExtensions		SEQUENCE {
					handoverFromUTRANCommand-GSM-v860ext
													HandoverFromUTRANCommand-GSM-v860ext-IEs,
					nonCriticalExtensions			SEQUENCE {}	OPTIONAL
				}	OPTIONAL
			}	OPTIONAL
		}	OPTIONAL
	},
	later-than-r3					SEQUENCE {
		rrc-TransactionIdentifier		RRC-TransactionIdentifier,
		criticalExtensions				CHOICE {
			r6								SEQUENCE {
				handoverFromUTRANCommand-GSM-r6		HandoverFromUTRANCommand-GSM-r6-IEs,
				handoverFromUTRANCommand-GSM-r6-add-ext		BIT STRING	OPTIONAL,
				v860NonCriticalExtensions		SEQUENCE {
					handoverFromUTRANCommand-GSM-v860ext
													HandoverFromUTRANCommand-GSM-v860ext-IEs,
					nonCriticalExtensions			SEQUENCE {}	OPTIONAL
				}	OPTIONAL
			},
			criticalExtensions				SEQUENCE {}
		}
	}
}

HandoverFromUTRANCommand-GSM-r3-IEs ::= SEQUENCE {
	-- User equipment IEs
		rrc-TransactionIdentifier		RRC-TransactionIdentifier,
		activationTime					ActivationTime						OPTIONAL,
	-- Radio bearer IEs
		toHandoverRAB-Info				RAB-Info							OPTIONAL,
	-- Measurement IEs
		frequency-band					Frequency-Band,
	-- Other IEs
		gsm-message						CHOICE {
			-- In the single-GSM-Message case the following rules apply:
			-- 1> the GSM message directly follows the basic production; the final padding that
			--    results when PER encoding the abstract syntax value is removed prior to appending 
			--    the GSM message.
			-- 2> the RRC message excluding the GSM part, does not contain a length determinant; 
			--    there is no explicit parameter indicating the size of the included GSM message.
			-- 3> depending on need, final padding (all "0"s) is added to ensure the final result
			--    comprises a full number of octets
			single-GSM-Message				SEQUENCE {},
			gsm-MessageList					SEQUENCE {
				gsm-Messages					GSM-MessageList
			}
		}
}

HandoverFromUTRANCommand-GSM-r6-IEs ::= SEQUENCE {
	-- User equipment IEs
		activationTime					ActivationTime						OPTIONAL,
	-- Radio bearer IEs
		toHandoverRAB-Info				RAB-InformationList-r6				OPTIONAL,
	-- Measurement IEs
		frequency-band					Frequency-Band,
	-- Other IEs
		gsm-message						CHOICE {
			-- In the single-GSM-Message case the following rules apply:
			-- 1> the GSM message directly follows the basic production; the final padding that
			--    results when PER encoding the abstract syntax value is removed prior to appending 
			--    the GSM message.
			-- 2> the RRC message excluding the GSM part, does not contain a length determinant; 
			--    there is no explicit parameter indicating the size of the included GSM message.
			-- 3> depending on need, final padding (all "0"s) is added to ensure the final result
			--    comprises a full number of octets
			single-GSM-Message				SEQUENCE {},
			gsm-MessageList					SEQUENCE {
				gsm-Messages					GSM-MessageList
			}
		},
		geran-SystemInfoType				CHOICE	{		
			sI									GERAN-SystemInformation,
			pSI									GERAN-SystemInformation
		}		OPTIONAL
}

HandoverFromUTRANCommand-GSM-v690ext-IEs ::= SEQUENCE {
		geran-SystemInfoType				CHOICE	{		
			sI									GERAN-SystemInformation,
			pSI									GERAN-SystemInformation
		}		OPTIONAL
}

HandoverFromUTRANCommand-GSM-v860ext-IEs ::= SEQUENCE {
	sr-vcc-SecurityRABInfo				SR-VCC-SecurityRABInfo-v860ext		OPTIONAL
}

HandoverFromUTRANCommand-GERANIu ::= SEQUENCE {
	rrc-TransactionIdentifier		RRC-TransactionIdentifier,
	handoverFromUTRANCommand-GERANIu	CHOICE {
		r5									SEQUENCE {
			handoverFromUTRANCommand-GERANIu-r5
											HandoverFromUTRANCommand-GERANIu-r5-IEs,
			-- UTRAN should not include the IE nonCriticalExtensions when it sets
			-- the IE geranIu-message included in handoverFromUTRANCommand-GERANIu-r5 to 
			-- single-GERANIu-Message
			-- The UE behaviour upon receiving a message including this combination of IE values is
			-- not specified
			nonCriticalExtensions			SEQUENCE {}	OPTIONAL
		},
		later-than-r5					SEQUENCE {
			criticalExtensions				SEQUENCE {}
		}
	}
}

HandoverFromUTRANCommand-GERANIu-r5-IEs ::= SEQUENCE {
	-- User equipment IEs
		activationTime					ActivationTime						OPTIONAL,
	-- Measurement IEs
		frequency-Band					Frequency-Band,
	-- Other IEs
		geranIu-Message						CHOICE {
			-- In the single-GERANIu-Message case the following rules apply:
			-- 1> the GERAN Iu message directly follows the basic production; the final padding that
			--    results when PER encoding the abstract syntax value is removed prior to appending 
			--    the GERAN Iu message.
			-- 2> the RRC message excluding the GERAN Iu part does not contain a length determinant; 
--    there is no explicit parameter indicating the size of the included GERAN Iu
--    message.
			-- 3> depending on need, final padding (all "0"s) is added to ensure the final result
			--    comprises a full number of octets.
			single-GERANIu-Message			SEQUENCE {},
			geranIu-MessageList				SEQUENCE {
				geranIu-Messages				GERANIu-MessageList
			}
		}
}

HandoverFromUTRANCommand-CDMA2000 ::= CHOICE {
	r3								SEQUENCE {
		handoverFromUTRANCommand-CDMA2000-r3
										HandoverFromUTRANCommand-CDMA2000-r3-IEs,
		laterNonCriticalExtensions			SEQUENCE {
			-- Container for additional R99 extensions 
			handoverFromUTRANCommand-CDMA2000-r3-add-ext
												BIT STRING		OPTIONAL,
			nonCriticalExtensions				SEQUENCE {}		OPTIONAL
		}	OPTIONAL
	},
	later-than-r3					SEQUENCE {
		rrc-TransactionIdentifier		RRC-TransactionIdentifier,
		criticalExtensions				SEQUENCE {}
	}
}

HandoverFromUTRANCommand-CDMA2000-r3-IEs ::= SEQUENCE {
	-- User equipment IEs
		rrc-TransactionIdentifier		RRC-TransactionIdentifier,
		activationTime					ActivationTime						OPTIONAL,
	-- Radio bearer IEs
		toHandoverRAB-Info				RAB-Info							OPTIONAL,
	-- Other IEs
		cdma2000-MessageList			CDMA2000-MessageList
}

HandoverFromUTRANCommand-EUTRA ::= SEQUENCE {
	rrc-TransactionIdentifier		RRC-TransactionIdentifier,
	criticalExtensions				CHOICE {
		r8								SEQUENCE {
			handoverFromUTRANCommand-EUTRA-r8	HandoverFromUTRANCommand-EUTRA-r8-IEs,
			handoverFromUTRANCommand-EUTRA-r8-add-ext
											BIT STRING		OPTIONAL,
			nonCriticalExtensions			SEQUENCE {}		OPTIONAL
		},
		criticalExtensions				CHOICE {
			r11								SEQUENCE {
				handoverFromUTRANCommand-EUTRA-r11	HandoverFromUTRANCommand-EUTRA-r11-IEs,
				handoverFromUTRANCommand-EUTRA-r11-add-ext	BIT STRING		OPTIONAL,
				nonCriticalExtensions			SEQUENCE {}		OPTIONAL
			},
			criticalExtensions				SEQUENCE {}
		}
	}
}

HandoverFromUTRANCommand-EUTRA-r8-IEs ::= SEQUENCE {
	-- User equipment IEs
		activationTime					ActivationTime						OPTIONAL,
	-- Radio bearer IEs
		toHandoverRAB-Info				RAB-InformationList					OPTIONAL,
	-- Other IEs
		eutra-Message					OCTET STRING
}

HandoverFromUTRANCommand-EUTRA-r11-IEs ::= SEQUENCE {
	-- User equipment IEs
		rsr-vcc-Info					RSR-VCC-Info 						OPTIONAL,
		activationTime					ActivationTime						OPTIONAL,
	-- Radio bearer IEs
		toHandoverRAB-Info				RAB-InformationList					OPTIONAL,
	-- Other IEs
		eutra-Message					OCTET STRING
}

-- ***************************************************
--
-- HANDOVER FROM UTRAN FAILURE
--
-- ***************************************************

HandoverFromUTRANFailure ::= SEQUENCE {
	-- User equipment IEs
		rrc-TransactionIdentifier		RRC-TransactionIdentifier,
	-- Other IEs
		interRAT-HO-FailureCause		InterRAT-HO-FailureCause			OPTIONAL,
		-- In case the interRATMessage to be transferred is for GERAN Iu mode, the
		-- message should be placed in the HandoverFromUtranFailure-v590ext-IEs
		-- non-critical extension container.
		-- In case the interRATMessage to be transferred is for E-UTRA, the
		-- message should be placed in the HandoverFromUtranFailure-v860ext-IEs
		-- non-critical extension container.
		interRATMessage					CHOICE {
			gsm								SEQUENCE {
				gsm-MessageList						GSM-MessageList
			},
			cdma2000							SEQUENCE {
				cdma2000-MessageList				CDMA2000-MessageList
			}
		}				OPTIONAL,
		laterNonCriticalExtensions		SEQUENCE {
			-- Container for additional R99 extensions
			handoverFromUTRANFailure-r3-add-ext		BIT STRING	OPTIONAL,
			v590NonCriticalExtensions		SEQUENCE {
				handoverFromUTRANFailure-v590ext	HandoverFromUtranFailure-v590ext-IEs,
				v860NonCriticalExtensions		SEQUENCE {
					handoverFromUTRANFailure-v860ext	HandoverFromUtranFailure-v860ext-IEs,
					nonCriticalExtensions			SEQUENCE {}		OPTIONAL
				}	OPTIONAL
			}	OPTIONAL
		}	OPTIONAL
}

HandoverFromUtranFailure-v590ext-IEs ::= SEQUENCE {
	geranIu-MessageList						GERANIu-MessageList			OPTIONAL
}

HandoverFromUtranFailure-v860ext-IEs ::= SEQUENCE {
	eutra-Message							OCTET STRING				OPTIONAL
}

-- ***************************************************
--
-- INTER RAT HANDOVER INFO
--
-- ***************************************************

InterRATHandoverInfo ::= SEQUENCE {
	-- This structure is defined for historical reasons, backward compatibility with 44.018
	predefinedConfigStatusList		CHOICE {
		absent							NULL,
		present							PredefinedConfigStatusList
	},
	uE-SecurityInformation			CHOICE {
		absent							NULL,
		present							UE-SecurityInformation
	},
	ue-CapabilityContainer			CHOICE {
		absent							NULL,
		-- present is an octet aligned string containing IE UE-RadioAccessCapabilityInfo
		present							OCTET STRING (SIZE (0..63))
	},
	-- Non critical extensions
	v390NonCriticalExtensions		CHOICE {
		absent							NULL,
		present							SEQUENCE {
			interRATHandoverInfo-v390ext	InterRATHandoverInfo-v390ext-IEs,
			v3a0NonCriticalExtensions		SEQUENCE  {
				interRATHandoverInfo-v3a0ext	InterRATHandoverInfo-v3a0ext-IEs,
				laterNonCriticalExtensions		SEQUENCE {
					interRATHandoverInfo-v3d0ext 	InterRATHandoverInfo-v3d0ext-IEs,
					-- Container for additional R99 extensions
					interRATHandoverInfo-r3-add-ext		BIT STRING
								(CONTAINING InterRATHandoverInfo-r3-add-ext-IEs)	OPTIONAL,
					v3g0NonCriticalExtensions			SEQUENCE {
						interRATHandoverInfo-v3g0ext	InterRATHandoverInfo-v3g0ext-IEs,
						v4b0NonCriticalExtensions		SEQUENCE {
							interRATHandoverInfo-v4b0ext	InterRATHandoverInfo-v4b0ext-IEs,
							v4d0NonCriticalExtensions		SEQUENCE {
								interRATHandoverInfo-v4d0ext	InterRATHandoverInfo-v4d0ext-IEs,
								-- Reserved for future non critical extension
								v590NonCriticalExtensions		SEQUENCE {
									interRATHandoverInfo-v590ext
																InterRATHandoverInfo-v590ext-IEs,
									v690NonCriticalExtensions		SEQUENCE {
										interRATHandoverInfo-v690ext
																InterRATHandoverInfo-v690ext-IEs,
										v6b0NonCriticalExtensions		
										InterRATHandoverInfo-NonCriticalExtension-v6b0-IEs	OPTIONAL
									}	OPTIONAL
								}	OPTIONAL
							}	OPTIONAL
						}	OPTIONAL
					}	OPTIONAL
				}	OPTIONAL
			}	OPTIONAL
		}
	}
}

InterRATHandoverInfo-v390ext-IEs ::= SEQUENCE {
	-- User equipment IEs
		ue-RadioAccessCapability-v380ext	UE-RadioAccessCapability-v380ext		OPTIONAL,
		dl-PhysChCapabilityFDD-v380ext		DL-PhysChCapabilityFDD-v380ext
}

InterRATHandoverInfo-v3a0ext-IEs ::= SEQUENCE {
	-- User equipment IEs
		ue-RadioAccessCapability-v3a0ext	UE-RadioAccessCapability-v3a0ext		OPTIONAL
}

InterRATHandoverInfo-v3d0ext-IEs ::= SEQUENCE {
	-- User equipment IEs
		uESpecificBehaviourInformation1interRAT	UESpecificBehaviourInformation1interRAT	OPTIONAL
}

InterRATHandoverInfo-v3g0ext-IEs ::= SEQUENCE {
	-- User equipment IEs
		ue-RadioAccessCapability-v3g0ext	UE-RadioAccessCapability-v3g0ext		OPTIONAL
}

InterRATHandoverInfo-r3-add-ext-IEs ::= SEQUENCE {
		interRATHandoverInfo-v690ext1		InterRATHandoverInfo-v690ext1-IEs,
		v7e0NonCriticalExtensions			SEQUENCE {
			interRATHandoverInfo-v7e0ext		InterRATHandoverInfo-v7e0ext-IEs,
			v7f0NonCriticalExtensions			SEQUENCE {
				interRATHandoverInfo-v7f0ext		InterRATHandoverInfo-v7f0ext-IEs,
				va40NonCriticalExtensions			SEQUENCE {
					interRATHandoverInfo-va40ext		InterRATHandoverInfoBand-va40ext-IEs,
					nonCriticalExtensions				SEQUENCE {}		OPTIONAL
				}		OPTIONAL
			}		OPTIONAL
		}		OPTIONAL
}

InterRATHandoverInfo-v4b0ext-IEs ::= SEQUENCE {
	-- User equipment IEs
		accessStratumReleaseIndicator		AccessStratumReleaseIndicator
}

InterRATHandoverInfo-v4d0ext-IEs ::= SEQUENCE {
	-- User equipment IEs
	tdd128-RF-Capability				RadioFrequencyBandTDDList		OPTIONAL
}

InterRATHandoverInfo-v590ext-IEs ::= SEQUENCE {
	-- User equipment IEs
		predefinedConfigStatusListComp		PredefinedConfigStatusListComp			OPTIONAL,
		ue-RadioAccessCapabilityComp		UE-RadioAccessCapabilityComp			OPTIONAL
}

InterRATHandoverInfo-v690ext1-IEs ::= SEQUENCE {
	-- User equipment IEs
		ue-RadioAccessCapability-v650ext		UE-RadioAccessCapability-v650ext	OPTIONAL
}

InterRATHandoverInfo-v690ext-IEs ::= SEQUENCE {
	-- User equipment IEs
		ue-SecurityInformation2				UE-SecurityInformation2					OPTIONAL,
		ue-RadioAccessCapabilityComp		UE-RadioAccessCapabilityComp-ext		OPTIONAL,
		ue-RadioAccessCapabilityComp2		UE-RadioAccessCapabilityComp2
}

InterRATHandoverInfo-NonCriticalExtension-v6b0-IEs ::=	SEQUENCE {
	interRATHandoverInfo-v6b0ext		InterRATHandoverInfo-v6b0ext-IEs,
	v6e0NonCriticalExtensions			SEQUENCE {
		interRATHandoverInfo-v6e0ext		InterRATHandoverInfo-v6e0ext-IEs,
		v770NonCriticalExtensions			SEQUENCE {
			interRATHandoverInfo-v770ext		InterRATHandoverInfo-v770ext-IEs,
			v790nonCriticalExtensions			SEQUENCE {
				interRATHandoverInfo-v790ext		InterRATHandoverInfo-v790ext-IEs,
				v860NonCriticalExtensions			SEQUENCE {
					interRATHandoverInfo-v860ext		InterRATHandoverInfo-v860ext-IEs,
					v880NonCriticalExtensions			SEQUENCE {
						interRATHandoverInfo-v880ext		InterRATHandoverInfo-v880ext-IEs,
						v920NonCriticalExtensions			SEQUENCE {
							interRATHandoverInfo-v920ext		InterRATHandoverInfo-v920ext-IEs,
							v8b0NonCriticalExtensions			SEQUENCE {
								interRATHandoverInfo-v8b0ext
																InterRATHandoverInfo-v8b0ext-IEs,
								v950NonCriticalExtensions			SEQUENCE {
									interRATHandoverInfo-v950ext
																InterRATHandoverInfo-v950ext-IEs,
									va40NonCriticalExtensions			SEQUENCE {
										interRATHandoverInfo-va40ext
																InterRATHandoverInfo-va40ext-IEs,
										va80NonCriticalExtensions			SEQUENCE {
											interRATHandoverInfo-va80ext
																InterRATHandoverInfo-va80ext-IEs,
											vb50NonCriticalExtensions			SEQUENCE {
												interRATHandoverInfo-vb50ext
																InterRATHandoverInfo-vb50ext-IEs,
												nonCriticalExtensions			SEQUENCE {} OPTIONAL
											}	OPTIONAL
										}	OPTIONAL
									}	OPTIONAL
								}	OPTIONAL
							}	OPTIONAL
						}	OPTIONAL
					}	OPTIONAL
				}	OPTIONAL
			}	OPTIONAL
		}	OPTIONAL
	}	OPTIONAL
}

InterRATHandoverInfo-v6b0ext-IEs ::= SEQUENCE {
	-- User equipment IEs
		supportForSIB11bis					ENUMERATED { true }			OPTIONAL
}

InterRATHandoverInfo-v6e0ext-IEs ::= SEQUENCE {
	-- User equipment IEs
		supportForFDPCH						ENUMERATED { true }			OPTIONAL
}

InterRATHandoverInfo-v770ext-IEs ::= SEQUENCE {
		ue-RadioAccessCapabilityInfo		UE-RadioAccessCapabilityInfo-v770ext	OPTIONAL,
		ue-RadioAccessCapabilityComp		UE-RadioAccessCapabilityComp-v770ext	OPTIONAL,
		ue-RadioAccessCapabilityComp2		UE-RadioAccessCapabilityComp2-v770ext	OPTIONAL
}

InterRATHandoverInfo-v790ext-IEs ::= SEQUENCE {
	-- User equipment IEs
		supportForEDPCCHPowerBoosting		ENUMERATED { true }						OPTIONAL
}

InterRATHandoverInfo-v7e0ext-IEs ::=	SEQUENCE {
	-- User equipment IEs
		ue-RadioAccessCapability			UE-RadioAccessCapability-v7e0ext		OPTIONAL
}

InterRATHandoverInfo-v7f0ext-IEs ::=	SEQUENCE {
	-- User equipment IEs
		ue-RadioAccessCapability			UE-RadioAccessCapability-v7f0ext		OPTIONAL,
		ue-RadioAccessCapabilityComp2		UE-RadioAccessCapabilityComp2-v7f0ext	OPTIONAL
}

InterRATHandoverInfo-v860ext-IEs ::=	SEQUENCE {
		ue-RadioAccessCapabilityInfo		UE-RadioAccessCapability-v860ext		OPTIONAL,
		ue-RadioAccessCapabilityComp2		UE-RadioAccessCapabilityComp2-v860ext	OPTIONAL
}

InterRATHandoverInfo-v880ext-IEs ::=	SEQUENCE {
	-- UE radio access capability
		ue-RadioAccessCapabilityInfo			UE-RadioAccessCapability-v880ext		OPTIONAL,
		ue-RadioAccessCapabilityInfo-TDD128		UE-RadioAccessCapabilityComp-TDD128		OPTIONAL
}

InterRATHandoverInfo-v920ext-IEs ::=	SEQUENCE {
		ue-RadioAccessCapabilityInfo		UE-RadioAccessCapability-v920ext		OPTIONAL,
		ue-RadioAccessCapabilityComp2		UE-RadioAccessCapabilityComp2-v920ext	OPTIONAL
}

InterRATHandoverInfo-v8b0ext-IEs ::=	SEQUENCE {
	-- UE radio access capability
		ue-RadioAccessCapabilityInfo		UE-RadioAccessCapabilityInfo-TDD128-v8b0ext	OPTIONAL
}

InterRATHandoverInfo-v950ext-IEs ::=	SEQUENCE {
	-- User equipment IEs
		pdcp-Capability						PDCP-Capability-r4-ext					OPTIONAL
}

InterRATHandoverInfo-va40ext-IEs ::=	SEQUENCE {
		ue-RadioAccessCapabilityInfo		UE-RadioAccessCapability-va40ext		OPTIONAL,
		ue-RadioAccessCapabilityComp2		UE-RadioAccessCapabilityComp2-va40ext	OPTIONAL
}

InterRATHandoverInfoBand-va40ext-IEs ::=	SEQUENCE {
	-- User equipment IEs
		ue-RadioAccessCapabBand				UE-RadioAccessCapabBand-va40ext 		OPTIONAL,
		rf-CapabilityFDDComp				RF-CapabBandListFDDComp-ext2 			OPTIONAL
}

InterRATHandoverInfo-va80ext-IEs ::=	SEQUENCE {
		ue-RadioAccessCapabilityInfo-va80ext	UE-RadioAccessCapability-va80ext	OPTIONAL
}

InterRATHandoverInfo-vb50ext-IEs ::=	SEQUENCE {
		ue-RadioAccessCapabilityInfo-vb50ext	UE-RadioAccessCapability-vb50ext	OPTIONAL,
		ue-RadioAccessCapabilityComp2		UE-RadioAccessCapabilityComp2-vb50ext	OPTIONAL,
		ue-RadioAccessCapabilityInfo-TDD128	UE-RadioAccessCapabilityInfo-TDD128-vb50ext	OPTIONAL
}

-- ***************************************************
--
-- MEASUREMENT CONTROL
--
-- ***************************************************

MeasurementControl ::= CHOICE {
	-- The Rel-4 functionality of UE Positioning OTDOA AssistanceData TDD is only available
	-- in the later-than-r3 branch of this message (i.e. through the use of the IE
	-- ue-Positioning-OTDOA-AssistanceData-r4)
	r3								SEQUENCE {
		measurementControl-r3			MeasurementControl-r3-IEs,
		v390nonCriticalExtensions		SEQUENCE {
			measurementControl-v390ext		MeasurementControl-v390ext,
			v3a0NonCriticalExtensions			SEQUENCE {
				measurementControl-v3a0ext			MeasurementControl-v3a0ext,
				laterNonCriticalExtensions		SEQUENCE {
					-- Container for additional R99 extensions
					measurementControl-r3-add-ext		BIT STRING	OPTIONAL,
					v4b0NonCriticalExtensions			SEQUENCE{
						-- The content of the v4b0 non-critical extension has been removed. If sent 
						-- to a UE of AS release 4, the UE behaviour is unspecified. A UE of AS 
						-- release 5 onward shall comply with the v4b0 and later extensions in this 
						-- branch of the message.
						v590NonCriticalExtensions		SEQUENCE {
							measurementControl-v590ext		MeasurementControl-v590ext-IEs,
							v5b0NonCriticalExtensions		SEQUENCE {
								measurementControl-v5b0ext		MeasurementControl-v5b0ext-IEs,
								nonCriticalExtensions			SEQUENCE {}		OPTIONAL
							}						OPTIONAL
						}						OPTIONAL
					}						OPTIONAL
				}						OPTIONAL
			}						OPTIONAL
		}						OPTIONAL
	},
	later-than-r3					SEQUENCE {
		-- Least significant part of extended "RRC transaction identifier" (Rel-5 onward)
		rrc-TransactionIdentifier		RRC-TransactionIdentifier,
		criticalExtensions				CHOICE {
			r4								SEQUENCE {
				measurementControl-r4			MeasurementControl-r4-IEs,
				v4d0NonCriticalExtensions			SEQUENCE {
					-- Container for adding non critical extensions after freezing REL-5
					measurementControl-r4-add-ext		BIT STRING		OPTIONAL,
					v590NonCriticalExtensions		SEQUENCE{
						measurementControl-v590ext		MeasurementControl-v590ext-IEs,
						v5b0NonCriticalExtensions		SEQUENCE {
							measurementControl-v5b0ext		MeasurementControl-v5b0ext-IEs,
							nonCriticalExtensions			SEQUENCE {}		OPTIONAL
						}	OPTIONAL
					}	OPTIONAL
				}	OPTIONAL
			},
			later-than-r4					SEQUENCE {
				-- Most significant part of extended "RRC transaction identifier" (MSP):
				-- extended "RRC transaction identifier" =
				-- rrc-TransactionIdentifier-MSP * 4 + rrc-TransactionIdentifier
				rrc-TransactionIdentifier-MSP		RRC-TransactionIdentifier,
				criticalExtensions				CHOICE {
					r6								SEQUENCE {
						measurementControl-r6			MeasurementControl-r6-IEs,
						v6a0NonCriticalExtensions		SEQUENCE {
							measurementControl-v6a0ext		MeasurementControl-v6a0ext-IEs,
							nonCriticalExtensions			SEQUENCE {}		OPTIONAL
						}	OPTIONAL
					},
					criticalExtensions				CHOICE {
						r7								SEQUENCE {
							measurementControl-r7			MeasurementControl-r7-IEs,
							-- Container for adding non critical extensions after freezing REL-7
							measurementControl-r7-add-ext	BIT STRING		OPTIONAL,
							v7b0NonCriticalExtensions		SEQUENCE {
								measurementControl-v7b0ext		MeasurementControl-v7b0ext-IEs,
								nonCriticalExtensions			SEQUENCE {}		OPTIONAL
							}	OPTIONAL
						},
						criticalExtensions				CHOICE {
							r8								SEQUENCE {
								measurementControl-r8			MeasurementControl-r8-IEs,
								-- Container for adding non critical extensions after freezing REL-9
								measurementControl-r8-add-ext	BIT STRING		OPTIONAL,
								v8a0NonCriticalExtensions		SEQUENCE {
									measurementControl-v8a0ext		MeasurementControl-v8a0ext-IEs,
									vb50NonCriticalExtensions	SEQUENCE {
										measurementControl-vb50ext	MeasurementControl-vb50ext-IEs,
										nonCriticalExtensions			SEQUENCE {}		OPTIONAL
									}	OPTIONAL
								}	OPTIONAL
							},
							criticalExtensions				CHOICE {
								r9								SEQUENCE {
									measurementControl-r9			MeasurementControl-r9-IEs,
									-- Container for adding non critical extensions after freezing REL-10
									measurementControl-r9-add-ext	BIT STRING		OPTIONAL,
									v970NonCriticalExtensions			SEQUENCE {
										measurementControl-v970ext	
															MeasurementControl-v970ext-IEs,
										vb50NonCriticalExtensions	SEQUENCE {
											measurementControl-vb50ext	
																MeasurementControl-vb50ext-IEs,
											nonCriticalExtensions	SEQUENCE {}		OPTIONAL	
										}		OPTIONAL
									}		OPTIONAL
								},
								criticalExtensions				CHOICE	{
									r10								SEQUENCE	{
											measurementControl-r10			MeasurementControl-r10-IEs, 
											-- Container for adding non critical extensions after
											-- freezing REL-11
										measurementControl-r10-add-ext	BIT STRING		OPTIONAL, 
										vaa0NonCriticalExtensions			SEQUENCE {
											measurementControl-vaa0ext	
															MeasurementControl-vaa0ext-IEs,
											vab0NonCriticalExtensions			SEQUENCE {
												measurementControl-vab0ext	
																MeasurementControl-vab0ext-IEs,
												vb50NonCriticalExtensions	SEQUENCE {
													measurementControl-vb50ext		
														MeasurementControl-vb50ext-IEs,
													nonCriticalExtensions	SEQUENCE {}		OPTIONAL
												}	OPTIONAL
											}	OPTIONAL
										}	OPTIONAL
									},
									criticalExtensions				CHOICE	{
										r11								SEQUENCE	{
												measurementControl-r11				
																			MeasurementControl-r11-IEs, 
												-- Container for adding non critical extensions after
												-- freezing REL-12
											measurementControl-r11-add-ext	BIT STRING																										OPTIONAL,
											nonCriticalExtensions			SEQUENCE {}		OPTIONAL
										},
										criticalExtensions				SEQUENCE {}
									}
								}
							}
						}
					}
				}
			}
		}
	}
}

MeasurementControl-r3-IEs ::= SEQUENCE {
	-- User equipment IEs
		rrc-TransactionIdentifier		RRC-TransactionIdentifier,
	-- Measurement IEs
		measurementIdentity		MeasurementIdentity,
		-- TABULAR: The measurement type is included in MeasurementCommand.
		measurementCommand				MeasurementCommand,
		measurementReportingMode		MeasurementReportingMode			OPTIONAL,
		additionalMeasurementList		AdditionalMeasurementID-List		OPTIONAL,
	-- Physical channel IEs
		dpch-CompressedModeStatusInfo	DPCH-CompressedModeStatusInfo		OPTIONAL
}

MeasurementControl-v390ext ::= SEQUENCE {
		ue-Positioning-Measurement-v390ext		UE-Positioning-Measurement-v390ext	OPTIONAL
}

MeasurementControl-v3a0ext ::= SEQUENCE {
	sfn-Offset-Validity				SFN-Offset-Validity		OPTIONAL
}

MeasurementControl-r4-IEs ::= SEQUENCE {
	-- Measurement IEs
		measurementIdentity		MeasurementIdentity,
		-- TABULAR: The measurement type is included in measurementCommand.
		measurementCommand				MeasurementCommand-r4,
		measurementReportingMode		MeasurementReportingMode			OPTIONAL,
		additionalMeasurementList		AdditionalMeasurementID-List		OPTIONAL,
	-- Physical channel IEs
		dpch-CompressedModeStatusInfo	DPCH-CompressedModeStatusInfo		OPTIONAL
}

MeasurementControl-v590ext-IEs ::= SEQUENCE {
	measurementCommand-v590ext 			CHOICE {
		-- the choice "intra-frequency" shall be used for the case of intra-frequency measurement,
		-- as well as when intra-frequency events are configured for inter-frequency measurement
		intra-frequency						Intra-FreqEventCriteriaList-v590ext,
		inter-frequency						Inter-FreqEventCriteriaList-v590ext
	}		OPTIONAL,
	intraFreqReportingCriteria-1b-r5		IntraFreqReportingCriteria-1b-r5	OPTIONAL,
	intraFreqEvent-1d-r5					IntraFreqEvent-1d-r5				OPTIONAL,
	-- Most significant part of extended "RRC transaction identifier" (MSP):
	-- extended "RRC transaction identifier" =
	-- rrc-TransactionIdentifier-MSP-v590ext * 4 + rrc-TransactionIdentifier
	rrc-TransactionIdentifier-MSP-v590ext	RRC-TransactionIdentifier
}

MeasurementControl-v5b0ext-IEs ::= 	SEQUENCE {
	interRATCellInfoIndication			InterRATCellInfoIndication			OPTIONAL
}

MeasurementControl-r6-IEs ::= SEQUENCE {
	-- Measurement IEs
		measurementIdentity				MeasurementIdentity,
		-- TABULAR: The measurement type is included in measurementCommand.
		measurementCommand				MeasurementCommand-r6,
		measurementReportingMode		MeasurementReportingMode			OPTIONAL,
		additionalMeasurementList		AdditionalMeasurementID-List		OPTIONAL,
	-- Physical channel IEs
		dpch-CompressedModeStatusInfo	DPCH-CompressedModeStatusInfo		OPTIONAL
}

MeasurementControl-v6a0ext-IEs ::= SEQUENCE {
	intraFreqReportingCriteria-1b-r5		IntraFreqReportingCriteria-1b-r5	OPTIONAL
}


MeasurementControl-r7-IEs ::= SEQUENCE {
	-- Measurement IEs
		measurementIdentity				MeasurementIdentity,
		-- TABULAR: The measurement type is included in measurementCommand.
		measurementCommand				MeasurementCommand-r7,
		measurementReportingMode		MeasurementReportingMode			OPTIONAL,
		additionalMeasurementList		AdditionalMeasurementID-List		OPTIONAL,
	-- Physical channel IEs
		dpch-CompressedModeStatusInfo	DPCH-CompressedModeStatusInfo		OPTIONAL
}

MeasurementControl-v7b0ext-IEs ::= SEQUENCE {
	-- Measurement IEs
		newInterFreqCellList			NewInterFreqCellList-v7b0ext		OPTIONAL
}

MeasurementControl-r8-IEs ::= SEQUENCE {
	-- Measurement IEs
		measurementIdentity				MeasurementIdentity,
		-- TABULAR: The measurement type is included in measurementCommand.
		measurementCommand				MeasurementCommand-r8,
		measurementReportingMode		MeasurementReportingMode			OPTIONAL,
		additionalMeasurementList		AdditionalMeasurementID-List		OPTIONAL,
	-- Physical channel IEs
		dpch-CompressedModeStatusInfo	DPCH-CompressedModeStatusInfo		OPTIONAL
}

MeasurementControl-v8a0ext-IEs ::= SEQUENCE {
	-- Measurement IEs
		newIntraFreqCellList			NewIntraFreqCellList-LCR-v8a0ext		OPTIONAL,
		newInterFreqCellList			NewInterFreqCellList-LCR-v8a0ext		OPTIONAL
}

MeasurementControl-r9-IEs ::= SEQUENCE {
	-- Measurement IEs
	-- if the UE supports extended measurements, "measurementIdentity" 
	-- shall be ignored if "measurementIdentity" in MeasurementControl-v970ext-IEs
	-- is present, and the value of that element shall be used instead.
		measurementIdentity				MeasurementIdentity,
		-- TABULAR: The measurement type is included in measurementCommand.
		measurementCommand				MeasurementCommand-r9,
		measurementReportingMode		MeasurementReportingMode			OPTIONAL,
	-- if the UE supports extended measurements, "additionalMeasurementList" 
	-- shall be ignored if "additionalMeasurementList" in MeasurementControl-v970ext-IEs
	-- is present, and the value of that element shall be used instead.
		additionalMeasurementList		AdditionalMeasurementID-List		OPTIONAL,
		cellDCHMeasOccasionInfo-TDD128	CellDCHMeasOccasionInfo-TDD128-r9	OPTIONAL,
	-- Physical channel IEs
		dpch-CompressedModeStatusInfo	DPCH-CompressedModeStatusInfo		OPTIONAL
}

MeasurementControl-v970ext-IEs ::= SEQUENCE {
	-- Measurement IEs
		measurementIdentity				MeasurementIdentity-r9					OPTIONAL,
		additionalMeasurementList		AdditionalMeasurementID-List-r9			OPTIONAL
}

MeasurementControl-r10-IEs ::=	SEQUENCE {
	-- Measurement IEs
	-- if the UE supports extended measurements, "measurementIdentity" 
	-- shall be ignored if "measurementIdentity" in MeasurementControl-vab0ext-IEs
	-- is present, and the value of that element shall be used instead.
		measurementIdentity				MeasurementIdentity,
		-- TABULAR: The measurement type is included in measurementCommand.
		measurementCommand				MeasurementCommand-r10,
		measurementReportingMode		MeasurementReportingMode			OPTIONAL,
	-- if the UE supports extended measurements, "additionalMeasurementList" 
	-- shall be ignored if "additionalMeasurementList" in MeasurementControl-vab0ext-IEs
	-- is present, and the value of that element shall be used instead.
		additionalMeasurementList		AdditionalMeasurementID-List		OPTIONAL,
		cellDCHMeasOccasionInfo-TDD128	CellDCHMeasOccasionInfo-TDD128-r9	OPTIONAL,
	-- Physical channel IEs
		dpch-CompressedModeStatusInfo	DPCH-CompressedModeStatusInfo-r10		OPTIONAL
}

MeasurementControl-vaa0ext-IEs ::= SEQUENCE {
	-- Measurement IEs
	periodicalReportingCriteriaOnSecULFreq
										PeriodicalWithReportingCellStatusOnSecULFreq	OPTIONAL
}

MeasurementControl-vab0ext-IEs ::= MeasurementControl-v970ext-IEs

MeasurementControl-r11-IEs ::=	SEQUENCE {
	-- Measurement IEs
		measurementIdentity				MeasurementIdentity-r9,
		-- TABULAR: The measurement type is included in measurementCommand.
		measurementCommand				MeasurementCommand-r11,
		measurementReportingMode		MeasurementReportingMode			OPTIONAL,
		additionalMeasurementList		AdditionalMeasurementID-List-r9		OPTIONAL,
		cellDCHMeasOccasionInfo-TDD128	CellDCHMeasOccasionInfo-TDD128-r9	OPTIONAL,
	-- Physical channel IEs
		dpch-CompressedModeStatusInfo	DPCH-CompressedModeStatusInfo-r10		OPTIONAL
}

MeasurementControl-vb50ext-IEs ::= SEQUENCE {
	-- Measurement IEs
	interRATMeasurement					InterRATMeasurement-r11					OPTIONAL
}

-- ***************************************************
--
-- MEASUREMENT CONTROL FAILURE
--
-- ***************************************************

MeasurementControlFailure ::= SEQUENCE {
	-- User equipment IEs
		-- Least significant part of extended "RRC transaction identifier" (Rel-5 onward)
		rrc-TransactionIdentifier		RRC-TransactionIdentifier,
		failureCause					FailureCauseWithProtErr,
		laterNonCriticalExtensions		SEQUENCE {
			-- Container for additional R99 extensions
			measurementControlFailure-r3-add-ext		BIT STRING		OPTIONAL,
			v590NonCriticalExtensions		SEQUENCE {
				measurementControlFailure-v590ext		MeasurementControlFailure-v590ext-IEs,
				nonCriticalExtensions			SEQUENCE {}		OPTIONAL
			}	OPTIONAL
		}	OPTIONAL
}

MeasurementControlFailure-v590ext-IEs ::= SEQUENCE {
	-- Most significant part of extended "RRC transaction identifier" (MSP):
	-- extended "RRC transaction identifier" =
	-- rrc-TransactionIdentifier-MSP-v590ext * 4 + rrc-TransactionIdentifier
	-- If the rrc-TransactionIdentifier-MSP-v590ext was not received in the MEASUREMENT CONTROL 
	-- message, then the rrc-TransactionIdentifier-MSP-v590ext shall be set to zero
	rrc-TransactionIdentifier-MSP-v590ext	RRC-TransactionIdentifier
}

-- ***************************************************
--
-- MEASUREMENT REPORT
--
-- ***************************************************

MeasurementReport ::= SEQUENCE {
	-- Measurement IEs
	-- if the UE supports extended measurements, "measurementIdentity" 
	-- shall be ignored if "measurementIdentity" in MeasurementReport-v970ext-IEs
	-- is present, and the value of that element shall be used instead.
		measurementIdentity				MeasurementIdentity,
		measuredResults					MeasuredResults						OPTIONAL,
		measuredResultsOnRACH			MeasuredResultsOnRACH				OPTIONAL,
		additionalMeasuredResults		MeasuredResultsList					OPTIONAL,
		eventResults					EventResults						OPTIONAL,
	-- Non-critical extensions
		v390nonCriticalExtensions			SEQUENCE {
			measurementReport-v390ext		MeasurementReport-v390ext,
			laterNonCriticalExtensions		SEQUENCE {
				-- Container for additional R99 extensions
				measurementReport-r3-add-ext		BIT STRING		OPTIONAL,
				v4b0NonCriticalExtensions		SEQUENCE {
					measurementReport-v4b0ext		MeasurementReport-v4b0ext-IEs,
					-- Extension mechanism for non-Rel4 information
					v590NonCriticalExtensions	SEQUENCE {
						measurementReport-v590ext		MeasurementReport-v590ext-IEs,
						v5b0NonCriticalExtensions		SEQUENCE {
							measurementReport-v5b0ext		MeasurementReport-v5b0ext-IEs,
							v690NonCriticalExtensions			SEQUENCE {
								measurementReport-v690ext		MeasurementReport-v690ext-IEs,
								v770NonCriticalExtensions		SEQUENCE {
									measurementReport-v770ext		MeasurementReport-v770ext-IEs,
									v860NonCriticalExtensions		SEQUENCE {
										measurementReport-v860ext	MeasurementReport-v860ext-IEs,
										v920NonCriticalExtensions		SEQUENCE {
											measurementReport-v920ext	MeasurementReport-v920ext-IEs,
											v970NonCriticalExtensions		SEQUENCE {
												measurementReport-v970ext-IE	
																MeasurementReport-v970ext-IEs,
												va40NonCriticalExtensions		SEQUENCE {
													measurementReport-va40ext	
																MeasurementReport-va40ext-IEs,
													vb50NonCriticalExtensions		SEQUENCE {
														measurementReport-vb50ext	
																	MeasurementReport-vb50ext-IEs,
														nonCriticalExtensions
																	SEQUENCE {}		OPTIONAL
													}			OPTIONAL
												}			OPTIONAL
											}		OPTIONAL
										}		OPTIONAL
									}		OPTIONAL
								}		OPTIONAL
							}		OPTIONAL
						}		OPTIONAL
					}		OPTIONAL
				}		OPTIONAL
			}		OPTIONAL
		}		OPTIONAL
}

MeasurementReport-v390ext ::= SEQUENCE {
		measuredResults-v390ext			MeasuredResults-v390ext				OPTIONAL
}

MeasurementReport-v4b0ext-IEs ::= SEQUENCE {
	interFreqEventResults-LCR		InterFreqEventResults-LCR-r4-ext		OPTIONAL,
	-- additionalMeasuredResults-LCR shall contain measurement results and additional measurement
	-- results list.
	additionalMeasuredResults-LCR	MeasuredResultsList-LCR-r4-ext			OPTIONAL,
	-- dummy is not used in this version of the specification. It should not be sent and
	-- if received it should be ignored.
	dummy							PrimaryCPICH-Info						OPTIONAL
}

MeasurementReport-v590ext-IEs ::= SEQUENCE {
	measuredResults-v590ext				MeasuredResults-v590ext				OPTIONAL
}

MeasurementReport-v5b0ext-IEs ::= 	SEQUENCE {
	interRATCellInfoIndication			InterRATCellInfoIndication			OPTIONAL
}

MeasurementReport-v690ext-IEs ::= SEQUENCE {
	measuredResultsOnRACHinterFreq		MeasuredResultsOnRACHinterFreq		OPTIONAL
}

MeasurementReport-v770ext-IEs ::= SEQUENCE {
	measuredResults						MeasuredResults-v770ext				OPTIONAL,
	additionalMeasuredResults			MeasuredResultsList-v770xet			OPTIONAL,
	eventResults						EventResults-v770ext				OPTIONAL,
	ue-Positioning-OTDOA-MeasuredResults
										UE-Positioning-OTDOA-MeasuredResultsTDD-ext		OPTIONAL
}

MeasurementReport-v860ext-IEs ::= SEQUENCE {
	activationTime						ActivationTime						OPTIONAL,
	measuredResults						MeasuredResults-v860ext				OPTIONAL,
	additionalMeasuredResults			MeasuredResultsList-v860ext			OPTIONAL,
	eventResults						EventResults-v860ext				OPTIONAL,
	eutra-MeasuredResults				EUTRA-MeasuredResults				OPTIONAL,
	eutra-EventResults					EUTRA-EventResults					OPTIONAL
}

MeasurementReport-v920ext-IEs ::= SEQUENCE {
	cSGProximityIndication				CSGProximityIndication				OPTIONAL,
	measuredResults						MeasuredResults-v920ext				OPTIONAL,
	measuredResultsOnSecUlFreq			MeasuredResultsOnSecUlFreq			OPTIONAL,
	additionalMeasuredResults			MeasuredResultsList-v920ext			OPTIONAL,
	additionalMeasuredResultsOnSecUlFreq
										MeasuredResultsListOnSecUlFreq		OPTIONAL,
	eventResultsOnSecUlFreq				EventResultsOnSecUlFreq				OPTIONAL,
	eutra-MeasuredResults				EUTRA-MeasuredResults-v920ext		OPTIONAL
}

MeasurementReport-v970ext-IEs ::= SEQUENCE {
	measurementIdentity					MeasurementIdentityExt			OPTIONAL
}

MeasurementReport-va40ext-IEs ::= SEQUENCE {
	eventResults						EventResults-va40ext				OPTIONAL,
	loggedMeasAvailable					ENUMERATED { true }					OPTIONAL,
	loggedANRResultsAvailable			ENUMERATED { true }					OPTIONAL
}

MeasurementReport-vb50ext-IEs ::= SEQUENCE {
	-- Measurement IEs
	measuredResultsOnRACHEUTRAFreq		MeasuredResultsOnRACH-EUTRAFreq		OPTIONAL,
	eutra-EventResultsForCELLFACH			EUTRA-EventResultsForCELLFACH				OPTIONAL,
	cSGProximityIndication					CSGProximityIndication-vb50ext				OPTIONAL,
	eutra-MeasuredResults					EUTRA-MeasuredResults-vb50ext				OPTIONAL,
	eutra-EventResults						EUTRA-EventResults-vb50ext					OPTIONAL
}

-- ***************************************************
--
-- PAGING TYPE 1
--
-- ***************************************************

PagingType1 ::= SEQUENCE {
	-- User equipment IEs
		pagingRecordList				PagingRecordList					OPTIONAL,
	-- Other IEs
		bcch-ModificationInfo			BCCH-ModificationInfo				OPTIONAL,
		laterNonCriticalExtensions		SEQUENCE {
			-- Container for additional R99 extensions
			pagingType1-r3-add-ext			BIT STRING		OPTIONAL,
			v590NonCriticalExtensions		SEQUENCE {
				pagingType1-v590ext				PagingType1-v590ext-IEs,
				v860NonCriticalExtensions		SEQUENCE {
					pagingType1-v860ext				PagingType1-v860ext-IEs,
					nonCriticalExtensions			SEQUENCE {}		OPTIONAL
				}	OPTIONAL
			}	OPTIONAL
		}	OPTIONAL
}

PagingType1-v590ext-IEs ::= SEQUENCE {
	-- User equipment IEs
		pagingRecord2List				PagingRecord2List-r5				OPTIONAL
}

PagingType1-v860ext-IEs ::= SEQUENCE {
	-- Other IEs
		etws-Information				ETWS-Information					OPTIONAL
}

-- ***************************************************
--
-- PAGING TYPE 2
--
-- ***************************************************

PagingType2 ::= SEQUENCE {
	-- User equipment IEs
		rrc-TransactionIdentifier		RRC-TransactionIdentifier,
		pagingCause						PagingCause,
	-- Core network IEs
		cn-DomainIdentity				CN-DomainIdentity,
		pagingRecordTypeID				PagingRecordTypeID,
		laterNonCriticalExtensions		SEQUENCE {
			-- Container for additional R99 extensions
			pagingType2-r3-add-ext			BIT STRING		OPTIONAL,
			nonCriticalExtensions			SEQUENCE {}		OPTIONAL
		}	OPTIONAL
}

-- ***************************************************
--
-- PHYSICAL CHANNEL RECONFIGURATION
--
-- ***************************************************

PhysicalChannelReconfiguration ::= CHOICE {
	r3								SEQUENCE {
		physicalChannelReconfiguration-r3
										PhysicalChannelReconfiguration-r3-IEs,
		v3a0NonCriticalExtensions			SEQUENCE {
			physicalChannelReconfiguration-v3a0ext		PhysicalChannelReconfiguration-v3a0ext,
			laterNonCriticalExtensions		SEQUENCE {
				-- Container for additional R99 extensions
				physicalChannelReconfiguration-r3-add-ext			BIT STRING		OPTIONAL,
				v4b0NonCriticalExtenstions			SEQUENCE {
					physicalChannelReconfiguration-v4b0ext
												PhysicalChannelReconfiguration-v4b0ext-IEs,
					v590NonCriticalExtenstions			SEQUENCE {
						physicalChannelReconfiguration-v590ext
													PhysicalChannelReconfiguration-v590ext-IEs,
						v690NonCriticalExtensions		SEQUENCE {
							physicalChannelReconfiguration-v690ext		
														PhysicalChannelReconfiguration-v690ext-IEs,
							v770NonCriticalExtensions		SEQUENCE {
								physicalChannelReconfiguration-v770ext
														PhysicalChannelReconfiguration-v770ext-IEs,
								nonCriticalExtensions					SEQUENCE {} OPTIONAL
							}	OPTIONAL
						}	OPTIONAL
					}	OPTIONAL
				}	OPTIONAL
			}	OPTIONAL
		}	OPTIONAL
	},
	later-than-r3					SEQUENCE {
		rrc-TransactionIdentifier		RRC-TransactionIdentifier,
			criticalExtensions				CHOICE {
			r4								SEQUENCE {
				physicalChannelReconfiguration-r4
												PhysicalChannelReconfiguration-r4-IEs,
				v4d0NonCriticalExtensions			SEQUENCE {
					-- Container for adding non critical extensions after freezing REL-5
					physicalChannelReconfiguration-r4-add-ext		BIT STRING		OPTIONAL,
					v590NonCriticalExtenstions			SEQUENCE {
						physicalChannelReconfiguration-v590ext
												PhysicalChannelReconfiguration-v590ext-IEs,
						v690NonCriticalExtensions		SEQUENCE {
							physicalChannelReconfiguration-v690ext		
														PhysicalChannelReconfiguration-v690ext-IEs,
							v770NonCriticalExtensions		SEQUENCE {
								physicalChannelReconfiguration-v770ext
														PhysicalChannelReconfiguration-v770ext-IEs,
								nonCriticalExtensions			SEQUENCE {}		OPTIONAL
							}	OPTIONAL
						}	OPTIONAL
					}	OPTIONAL
				}	OPTIONAL
			},
			criticalExtensions				CHOICE {
				r5								SEQUENCE {
					physicalChannelReconfiguration-r5
													PhysicalChannelReconfiguration-r5-IEs,
					-- Container for adding non critical extensions after freezing REL-6
					physicalChannelReconfiguration-r5-add-ext		BIT STRING		OPTIONAL,
					v690NonCriticalExtensions		SEQUENCE {
						physicalChannelReconfiguration-v690ext		
														PhysicalChannelReconfiguration-v690ext-IEs,
						v770NonCriticalExtensions		SEQUENCE {
							physicalChannelReconfiguration-v770ext
														PhysicalChannelReconfiguration-v770ext-IEs,
							nonCriticalExtensions			SEQUENCE {}		OPTIONAL
						}	OPTIONAL
					}	OPTIONAL
				},
				criticalExtensions				CHOICE {
					r6								SEQUENCE {
						physicalChannelReconfiguration-r6
														PhysicalChannelReconfiguration-r6-IEs,
						-- Container for adding non critical extensions after freezing REL-7
						physicalChannelReconfiguration-r6-add-ext		BIT STRING		OPTIONAL,
						v6b0NonCriticalExtensions		SEQUENCE {
							physicalChannelReconfiguration-v6b0ext
														PhysicalChannelReconfiguration-v6b0ext-IEs,
							v770NonCriticalExtensions		SEQUENCE {
								physicalChannelReconfiguration-v770ext
														PhysicalChannelReconfiguration-v770ext-IEs,
								nonCriticalExtensions			SEQUENCE {}		OPTIONAL
							}	OPTIONAL
						}	OPTIONAL
					},
					criticalExtensions				CHOICE {
						r7								SEQUENCE {
							physicalChannelReconfiguration-r7
														PhysicalChannelReconfiguration-r7-IEs,
							-- Container for adding non critical extensions after freezing REL-7
							physicalChannelReconfiguration-r7-add-ext	BIT STRING	OPTIONAL,
							v780NonCriticalExtensions		SEQUENCE {
								physicalChannelReconfiguration-v780ext
														PhysicalChannelReconfiguration-v780ext-IEs,
								v7d0NonCriticalExtensions		SEQUENCE {
									physicalChannelReconfiguration-v7d0ext
														PhysicalChannelReconfiguration-v7d0ext-IEs,
									v7f0NonCriticalExtensions		SEQUENCE {
										physicalChannelReconfiguration-v7f0ext
														PhysicalChannelReconfiguration-v7f0ext-IEs,
										v7g0NonCriticalExtensions		SEQUENCE {
											physicalChannelReconfiguration-v7g0ext
														PhysicalChannelReconfiguration-v7g0ext-IEs,
											nonCriticalExtensions			SEQUENCE {}		OPTIONAL
										}	OPTIONAL
									}	OPTIONAL
								}	OPTIONAL
							}	OPTIONAL
						},
						criticalExtensions				CHOICE {
							r8								SEQUENCE {
								physicalChannelReconfiguration-r8
															PhysicalChannelReconfiguration-r8-IEs,
								-- Container for adding non critical extensions after freezing REL-9
								physicalChannelReconfiguration-r8-add-ext	BIT STRING	OPTIONAL,
								v7d0NonCriticalExtensions		SEQUENCE {
									physicalChannelReconfiguration-v7d0ext
														PhysicalChannelReconfiguration-v7d0ext-IEs,
									v7f0NonCriticalExtensions		SEQUENCE {
										physicalChannelReconfiguration-v7f0ext
														PhysicalChannelReconfiguration-v7f0ext-IEs,
										v890NonCriticalExtensions		SEQUENCE {
											physicalChannelReconfiguration-v890ext
														PhysicalChannelReconfiguration-v890ext-IEs,
											v7g0NonCriticalExtensions		SEQUENCE {
												physicalChannelReconfiguration-v7g0ext
														PhysicalChannelReconfiguration-v7g0ext-IEs,
												v8a0NonCriticalExtensions		SEQUENCE {
													physicalChannelReconfiguration-v8a0ext
														PhysicalChannelReconfiguration-v8a0ext-IEs,
													nonCriticalExtensions			SEQUENCE {}		OPTIONAL
												}	OPTIONAL
											}	OPTIONAL
										}	OPTIONAL
									}	OPTIONAL
								}	OPTIONAL
							},
							criticalExtensions				CHOICE {
								r9								SEQUENCE {
									physicalChannelReconfiguration-r9
															PhysicalChannelReconfiguration-r9-IEs,
									-- Container for adding non critical extensions after 
									-- freezing REL-10
									physicalChannelReconfiguration-r9-add-ext
																			BIT STRING	OPTIONAL,
									v950NonCriticalExtensions		SEQUENCE {
										physicalChannelReconfiguration-v950ext
														PhysicalChannelReconfiguration-v950ext-IEs,
										nonCriticalExtensions			SEQUENCE {}			OPTIONAL
									}	OPTIONAL
								},
								criticalExtensions				CHOICE {
									r10								SEQUENCE {
										physicalChannelReconfiguration-r10
															PhysicalChannelReconfiguration-r10-IEs,
										-- Container for adding non critical extensions after 
										-- freezing REL-11
										physicalChannelReconfiguration-r10-add-ext
																			BIT STRING	OPTIONAL,
										vb50NonCriticalExtensions		SEQUENCE {
											physicalChannelReconfiguration-vb50ext
														PhysicalChannelReconfiguration-vb50ext-IEs,
											nonCriticalExtensions			SEQUENCE {}																										OPTIONAL
										}	OPTIONAL
									},
									criticalExtensions				CHOICE {
										r11								SEQUENCE {
											physicalChannelReconfiguration-r11
															PhysicalChannelReconfiguration-r11-IEs,
											-- Container for adding non critical extensions after 
											-- freezing REL-12
											physicalChannelReconfiguration-r11-add-ext
																			BIT STRING	OPTIONAL,
											nonCriticalExtensions			
																			SEQUENCE {}		OPTIONAL
										},
										criticalExtensions				SEQUENCE {}
									}
								}
							}
						}
					}
				}
			}
		}
	}
}

PhysicalChannelReconfiguration-r3-IEs ::= SEQUENCE {
	-- User equipment IEs
		rrc-TransactionIdentifier		RRC-TransactionIdentifier,
		integrityProtectionModeInfo		IntegrityProtectionModeInfo			OPTIONAL,
		cipheringModeInfo				CipheringModeInfo					OPTIONAL,
		activationTime					ActivationTime						OPTIONAL,
		new-U-RNTI						U-RNTI								OPTIONAL,
		new-C-RNTI						C-RNTI								OPTIONAL,
		rrc-StateIndicator				RRC-StateIndicator,
		utran-DRX-CycleLengthCoeff		UTRAN-DRX-CycleLengthCoefficient	OPTIONAL,
	-- Core network IEs
		cn-InformationInfo				CN-InformationInfo					OPTIONAL,
	-- UTRAN mobility IEs
		ura-Identity					URA-Identity						OPTIONAL,
	-- Radio bearer IEs
		dl-CounterSynchronisationInfo	DL-CounterSynchronisationInfo		OPTIONAL,
	-- Physical channel IEs
		frequencyInfo					FrequencyInfo						OPTIONAL,
		maxAllowedUL-TX-Power			MaxAllowedUL-TX-Power				OPTIONAL,
		-- Note: the reference to CPCH in the element name below is incorrect. The name is not
		-- changed to keep it aligned with R99.
		ul-ChannelRequirement			UL-ChannelRequirementWithCPCH-SetID		OPTIONAL,
		modeSpecificInfo				CHOICE {
			fdd								SEQUENCE {
				-- dummy is not used in this version of specification, it should
				-- not be sent and if received it should be ignored.
				dummy							DL-PDSCH-Information		OPTIONAL
			},
			tdd								NULL
		},
		dl-CommonInformation			DL-CommonInformation				OPTIONAL,
		dl-InformationPerRL-List		DL-InformationPerRL-List			OPTIONAL
}

PhysicalChannelReconfiguration-v3a0ext ::= SEQUENCE {
	-- The IE "new-DSCH-RNTI" should not be included in FDD mode, and if received the UE behaviour
	-- is unspecified
	new-DSCH-RNTI					DSCH-RNTI							OPTIONAL
}

PhysicalChannelReconfiguration-v4b0ext-IEs ::= SEQUENCE {
	-- Physical channel IEs
		-- dummy is not used in this version of the specification, it should
		-- not be sent and if received it should be ignored.
		dummy								SSDT-UL								OPTIONAL,
		-- The order of the RLs in IE cell-id-PerRL-List is the same as
		-- in IE DL-InformationPerRL-List included in this message
		cell-id-PerRL-List					CellIdentity-PerRL-List				OPTIONAL
}

PhysicalChannelReconfiguration-v590ext-IEs ::= SEQUENCE {
	-- Physical channel IEs
		dl-TPC-PowerOffsetPerRL-List	DL-TPC-PowerOffsetPerRL-List		OPTIONAL
}

PhysicalChannelReconfiguration-r4-IEs ::= SEQUENCE {
	-- User equipment IEs
		integrityProtectionModeInfo		IntegrityProtectionModeInfo			OPTIONAL,
		cipheringModeInfo				CipheringModeInfo					OPTIONAL,
		activationTime					ActivationTime						OPTIONAL,
		new-U-RNTI						U-RNTI								OPTIONAL,
		new-C-RNTI						C-RNTI								OPTIONAL,
		-- The IE "new-DSCH-RNTI" should not be included in FDD mode, and if received
		-- the UE behaviour is unspecified
		new-DSCH-RNTI					DSCH-RNTI							OPTIONAL,
		rrc-StateIndicator				RRC-StateIndicator,
		utran-DRX-CycleLengthCoeff		UTRAN-DRX-CycleLengthCoefficient	OPTIONAL,
	-- Core network IEs
		cn-InformationInfo				CN-InformationInfo					OPTIONAL,
	-- UTRAN mobility IEs
		ura-Identity					URA-Identity						OPTIONAL,
	-- Radio bearer IEs
		dl-CounterSynchronisationInfo	DL-CounterSynchronisationInfo		OPTIONAL,
	-- Physical channel IEs
		frequencyInfo					FrequencyInfo						OPTIONAL,
		maxAllowedUL-TX-Power			MaxAllowedUL-TX-Power				OPTIONAL,
		-- Note: the reference to CPCH in the element name below is incorrect. The name is not
		-- changed to keep it aligned with R99.
		ul-ChannelRequirement			UL-ChannelRequirementWithCPCH-SetID-r4	OPTIONAL,
		modeSpecificInfo				CHOICE {
			fdd								SEQUENCE {
				-- dummy is not used in this version of specification, it should
				-- not be sent and if received it should be ignored.
				dummy							DL-PDSCH-Information		OPTIONAL
			},
			tdd								NULL
		},
		dl-CommonInformation			DL-CommonInformation-r4				OPTIONAL,
		dl-InformationPerRL-List		DL-InformationPerRL-List-r4			OPTIONAL
}

PhysicalChannelReconfiguration-r5-IEs ::= SEQUENCE {
	-- User equipment IEs
		integrityProtectionModeInfo		IntegrityProtectionModeInfo			OPTIONAL,
		cipheringModeInfo				CipheringModeInfo					OPTIONAL,
		activationTime					ActivationTime						OPTIONAL,
		new-U-RNTI						U-RNTI								OPTIONAL,
		new-C-RNTI						C-RNTI								OPTIONAL,
		-- The IE "new-DSCH-RNTI" should not be included in FDD mode, and if received
		-- the UE behaviour is unspecified
		new-DSCH-RNTI					DSCH-RNTI							OPTIONAL,
		new-H-RNTI						H-RNTI								OPTIONAL,
		rrc-StateIndicator				RRC-StateIndicator,
		utran-DRX-CycleLengthCoeff		UTRAN-DRX-CycleLengthCoefficient	OPTIONAL,
	-- Core network IEs
		cn-InformationInfo				CN-InformationInfo					OPTIONAL,
	-- UTRAN mobility IEs
		ura-Identity					URA-Identity						OPTIONAL,
	-- Radio bearer IEs
		dl-CounterSynchronisationInfo	DL-CounterSynchronisationInfo-r5	OPTIONAL,
	-- Physical channel IEs
		frequencyInfo					FrequencyInfo						OPTIONAL,
		maxAllowedUL-TX-Power			MaxAllowedUL-TX-Power				OPTIONAL,
		-- Note: the reference to CPCH in the element name below is incorrect. The name is not
		-- changed to keep it aligned with R99.
		ul-ChannelRequirement			UL-ChannelRequirementWithCPCH-SetID-r5	OPTIONAL,
		modeSpecificInfo				CHOICE {
			fdd								SEQUENCE {
				-- dummy is not used in this version of specification, it should
				-- not be sent and if received it should be ignored.
				dummy							DL-PDSCH-Information		OPTIONAL
			},
			tdd								NULL
		},
		dl-HSPDSCH-Information			DL-HSPDSCH-Information				OPTIONAL,
		dl-CommonInformation			DL-CommonInformation-r5				OPTIONAL,
		dl-InformationPerRL-List		DL-InformationPerRL-List-r5			OPTIONAL
}

PhysicalChannelReconfiguration-r6-IEs ::= SEQUENCE {
	-- User equipment IEs
		integrityProtectionModeInfo		IntegrityProtectionModeInfo			OPTIONAL,
		cipheringModeInfo				CipheringModeInfo					OPTIONAL,
		activationTime					ActivationTime						OPTIONAL,
		delayRestrictionFlag			DelayRestrictionFlag				OPTIONAL,
		new-U-RNTI						U-RNTI								OPTIONAL,
		new-C-RNTI						C-RNTI								OPTIONAL,
		-- The IE "new-DSCH-RNTI" should not be included in FDD mode,
		-- and if received the UE behaviour is unspecified
		new-DSCH-RNTI					DSCH-RNTI							OPTIONAL,
		new-H-RNTI						H-RNTI								OPTIONAL,
		newPrimary-E-RNTI				E-RNTI								OPTIONAL,
		newSecondary-E-RNTI				E-RNTI								OPTIONAL,
		rrc-StateIndicator				RRC-StateIndicator,
		utran-DRX-CycleLengthCoeff		UTRAN-DRX-CycleLengthCoefficient	OPTIONAL,
	-- Core network IEs
		cn-InformationInfo				CN-InformationInfo-r6				OPTIONAL,
	-- UTRAN mobility IEs
		ura-Identity					URA-Identity						OPTIONAL,
	-- Radio bearer IEs
		dl-CounterSynchronisationInfo	DL-CounterSynchronisationInfo-r5	OPTIONAL,
	-- Physical channel IEs
		frequencyInfo					FrequencyInfo						OPTIONAL,
		maxAllowedUL-TX-Power			MaxAllowedUL-TX-Power				OPTIONAL,
		ul-DPCH-Info					UL-DPCH-Info-r6						OPTIONAL,
		ul-EDCH-Information				UL-EDCH-Information-r6				OPTIONAL,
		dl-HSPDSCH-Information			DL-HSPDSCH-Information-r6			OPTIONAL,
		dl-CommonInformation			DL-CommonInformation-r6				OPTIONAL,
		dl-InformationPerRL-List		DL-InformationPerRL-List-r6			OPTIONAL,
	-- MBMS IEs
		mbms-PL-ServiceRestrictInfo		MBMS-PL-ServiceRestrictInfo-r6		OPTIONAL
}

PhysicalChannelReconfiguration-v690ext-IEs ::= SEQUENCE {
	-- User Equipment IEs
		delayRestrictionFlag			DelayRestrictionFlag 				OPTIONAL,
	-- Core network IEs
		primary-plmn-Identity			PLMN-Identity						OPTIONAL,
	-- Physical channel IEs
		-- The IE harq-Preamble-Mode should not be used in the r3 and r4 versions of the message
		-- If included in the r3 or r4 version of the message, the UE should ignore the IE
		harq-Preamble-Mode				HARQ-Preamble-Mode					OPTIONAL,
		beaconPLEst						BEACON-PL-Est						OPTIONAL,
		postVerificationPeriod			ENUMERATED { true }					OPTIONAL,
		dhs-sync						DHS-Sync							OPTIONAL,
		timingMaintainedSynchInd		TimingMaintainedSynchInd			OPTIONAL,
	-- MBMS IEs
		mbms-PL-ServiceRestrictInfo		MBMS-PL-ServiceRestrictInfo-r6		OPTIONAL
}

PhysicalChannelReconfiguration-v6b0ext-IEs ::= SEQUENCE {
	-- Physical channel IEs
		dl-InformationPerRL-List-v6b0ext	DL-InformationPerRL-List-v6b0ext	OPTIONAL
}

PhysicalChannelReconfiguration-r7-IEs ::= SEQUENCE {
	-- User equipment IEs
		integrityProtectionModeInfo		IntegrityProtectionModeInfo-r7		OPTIONAL,
		cipheringModeInfo				CipheringModeInfo-r7				OPTIONAL,
		activationTime					ActivationTime						OPTIONAL,
		delayRestrictionFlag			DelayRestrictionFlag				OPTIONAL,
		new-U-RNTI						U-RNTI								OPTIONAL,
		new-C-RNTI						C-RNTI								OPTIONAL,
		-- The IE "new-DSCH-RNTI" should not be included in FDD mode,
		-- and if received the UE behaviour is unspecified
		new-DSCH-RNTI					DSCH-RNTI							OPTIONAL,
		new-H-RNTI						H-RNTI								OPTIONAL,
		newPrimary-E-RNTI				E-RNTI								OPTIONAL,
		newSecondary-E-RNTI				E-RNTI								OPTIONAL,
		rrc-StateIndicator				RRC-StateIndicator,
		ueMobilityStateIndicator		High-MobilityDetected				OPTIONAL,
		utran-DRX-CycleLengthCoeff		UTRAN-DRX-CycleLengthCoefficient-r7	OPTIONAL,
	-- Core network IEs
		cn-InformationInfo				CN-InformationInfo-r6				OPTIONAL,
	-- UTRAN mobility IEs
		ura-Identity					URA-Identity						OPTIONAL,
		supportForChangeOfUE-Capability	BOOLEAN								OPTIONAL,
		responseToChangeOfUE-Capability	ENUMERATED { true }					OPTIONAL,
	-- Radio bearer IEs
		dl-CounterSynchronisationInfo	DL-CounterSynchronisationInfo-r5	OPTIONAL,
	-- Physical channel IEs
		frequencyInfo					FrequencyInfo						OPTIONAL,
		multi-frequencyInfo				Multi-frequencyInfo-LCR-r7			OPTIONAL,
		dtx-drx-TimingInfo				DTX-DRX-TimingInfo-r7				OPTIONAL,
		dtx-drx-Info					DTX-DRX-Info-r7						OPTIONAL,
		hs-scch-LessInfo				HS-SCCH-LessInfo-r7					OPTIONAL,
		mimoParameters					MIMO-Parameters-r7					OPTIONAL,
		maxAllowedUL-TX-Power			MaxAllowedUL-TX-Power				OPTIONAL,
		ul-DPCH-Info					UL-DPCH-Info-r7						OPTIONAL,
		ul-EDCH-Information				UL-EDCH-Information-r7				OPTIONAL,
		dl-HSPDSCH-Information			DL-HSPDSCH-Information-r7			OPTIONAL,
		dl-CommonInformation			DL-CommonInformation-r7				OPTIONAL,
		dl-InformationPerRL-List		DL-InformationPerRL-List-r7			OPTIONAL,
	-- MBMS IEs
		mbms-PL-ServiceRestrictInfo		MBMS-PL-ServiceRestrictInfo-r6		OPTIONAL
}

PhysicalChannelReconfiguration-v770ext-IEs ::= SEQUENCE {
	-- User equipment IEs
		ueMobilityStateIndicator		High-MobilityDetected				OPTIONAL
}

PhysicalChannelReconfiguration-v780ext-IEs ::= SEQUENCE {
	-- Transport channel IEs
		harqInfo						HARQ-Info-r7						OPTIONAL,
	-- Physical channel IEs
		hs-DSCH-TBSizeTable				HS-DSCH-TBSizeTable					OPTIONAL
}

PhysicalChannelReconfiguration-v7d0ext-IEs ::= SEQUENCE {
	-- Physical channel IEs
		ul-EDCH-Information				UL-EDCH-Information-ext				OPTIONAL
}

PhysicalChannelReconfiguration-v7f0ext-IEs ::= SEQUENCE {
	-- Physical channel IEs
		mimoParameters					MIMO-Parameters-v7f0ext				OPTIONAL
}

PhysicalChannelReconfiguration-v7g0ext-IEs ::= SEQUENCE {
	-- Physical channel IEs
		mimoParameters					MIMO-Parameters-v7g0ext				OPTIONAL
}

PhysicalChannelReconfiguration-r8-IEs ::= SEQUENCE {
	-- User equipment IEs
		integrityProtectionModeInfo		IntegrityProtectionModeInfo-r7		OPTIONAL,
		cipheringModeInfo				CipheringModeInfo-r7				OPTIONAL,
		activationTime					ActivationTime						OPTIONAL,
		delayRestrictionFlag			DelayRestrictionFlag				OPTIONAL,
		new-U-RNTI						U-RNTI								OPTIONAL,
		new-C-RNTI						C-RNTI								OPTIONAL,
		-- The IE "new-DSCH-RNTI" should not be included in FDD mode,
		-- and if received the UE behaviour is unspecified
		new-DSCH-RNTI					DSCH-RNTI							OPTIONAL,
		new-H-RNTI						H-RNTI								OPTIONAL,
		newPrimary-E-RNTI				E-RNTI								OPTIONAL,
		newSecondary-E-RNTI				E-RNTI								OPTIONAL,
		rrc-StateIndicator				RRC-StateIndicator,
		ueMobilityStateIndicator		High-MobilityDetected				OPTIONAL,
		utran-DRX-CycleLengthCoeff		UTRAN-DRX-CycleLengthCoefficient-r7	OPTIONAL,
	-- Core network IEs
		cn-InformationInfo				CN-InformationInfo-r6				OPTIONAL,
	-- UTRAN mobility IEs
		ura-Identity					URA-Identity						OPTIONAL,
		supportForChangeOfUE-Capability	BOOLEAN								OPTIONAL,
		responseToChangeOfUE-Capability	ENUMERATED { true }					OPTIONAL,
	-- Radio bearer IEs
		dl-CounterSynchronisationInfo	DL-CounterSynchronisationInfo-r5	OPTIONAL,
	-- Transport channel IEs
		harqInfo						HARQ-Info-r7						OPTIONAL,
	-- Physical channel IEs
		frequencyInfo					FrequencyInfo						OPTIONAL,
		multi-frequencyInfo				Multi-frequencyInfo-LCR-r7			OPTIONAL,
		dtx-drx-TimingInfo				DTX-DRX-TimingInfo-r7				OPTIONAL,
		dtx-drx-Info					DTX-DRX-Info-r7						OPTIONAL,
		hs-scch-LessInfo				HS-SCCH-LessInfo-r7					OPTIONAL,
		mimoParameters					MIMO-Parameters-r8					OPTIONAL,
		maxAllowedUL-TX-Power			MaxAllowedUL-TX-Power				OPTIONAL,
		ul-DPCH-Info					UL-DPCH-Info-r7						OPTIONAL,
		ul-EDCH-Information				UL-EDCH-Information-r8				OPTIONAL,
		dl-HSPDSCH-Information			DL-HSPDSCH-Information-r8			OPTIONAL,
		dl-CommonInformation			DL-CommonInformation-r8				OPTIONAL,
		dl-InformationPerRL-List		DL-InformationPerRL-List-r8			OPTIONAL,
		dl-SecondaryCellInfoFDD			DL-SecondaryCellInfoFDD				OPTIONAL,
		controlChannelDRXInfo-TDD128	ControlChannelDRXInfo-TDD128-r8		OPTIONAL,
		sps-Information-TDD128			SPS-Information-TDD128-r8			OPTIONAL,
	-- MBMS IEs
		mbms-PL-ServiceRestrictInfo		MBMS-PL-ServiceRestrictInfo-r6		OPTIONAL
}

PhysicalChannelReconfiguration-v890ext-IEs ::= SEQUENCE {
	-- Physical channel IEs
		dl-SecondaryCellInfoFDD-v890ext		DL-SecondaryCellInfoFDD-v890ext		OPTIONAL,
		dl-HSPDSCH-Information				DL-HSPDSCH-Information-r8-ext		OPTIONAL
}

PhysicalChannelReconfiguration-v8a0ext-IEs ::= SEQUENCE {
	-- Physical channel IEs
		dl-HSPDSCH-Information				DL-HSPDSCH-Information-r8-ext2		OPTIONAL
}

PhysicalChannelReconfiguration-r9-IEs ::= SEQUENCE {
	-- User equipment IEs
		integrityProtectionModeInfo		IntegrityProtectionModeInfo-r7		OPTIONAL,
		cipheringModeInfo				CipheringModeInfo-r7				OPTIONAL,
		activationTime					ActivationTime						OPTIONAL,
		delayRestrictionFlag			DelayRestrictionFlag				OPTIONAL,
		new-U-RNTI						U-RNTI								OPTIONAL,
		new-C-RNTI						C-RNTI								OPTIONAL,
		-- The IE "new-DSCH-RNTI" should not be included in FDD mode,
		-- and if received the UE behaviour is unspecified
		new-DSCH-RNTI					DSCH-RNTI							OPTIONAL,
		new-H-RNTI						H-RNTI								OPTIONAL,
		newPrimary-E-RNTI				E-RNTI								OPTIONAL,
		newSecondary-E-RNTI				E-RNTI								OPTIONAL,
		rrc-StateIndicator				RRC-StateIndicator,
		ueMobilityStateIndicator		High-MobilityDetected				OPTIONAL,
		utran-DRX-CycleLengthCoeff		UTRAN-DRX-CycleLengthCoefficient-r7	OPTIONAL,
	-- Core network IEs
		cn-InformationInfo				CN-InformationInfo-r6				OPTIONAL,
	-- UTRAN mobility IEs
		ura-Identity					URA-Identity						OPTIONAL,
		supportForChangeOfUE-Capability	BOOLEAN								OPTIONAL,
		responseToChangeOfUE-Capability	ENUMERATED { true }					OPTIONAL,
	-- Radio bearer IEs
		dl-CounterSynchronisationInfo	DL-CounterSynchronisationInfo-r5	OPTIONAL,
	-- Transport channel IEs
		harqInfo						HARQ-Info-r7						OPTIONAL,
	-- Physical channel IEs
		frequencyInfo					FrequencyInfo						OPTIONAL,
		multi-frequencyInfo				Multi-frequencyInfo-LCR-r7			OPTIONAL,
		dtx-drx-TimingInfo				DTX-DRX-TimingInfo-r7				OPTIONAL,
		dtx-drx-Info					DTX-DRX-Info-r7						OPTIONAL,
		hs-scch-LessInfo				HS-SCCH-LessInfo-r7					OPTIONAL,
		mimoParameters					MIMO-Parameters-r9					OPTIONAL,
		controlChannelDRXInfo-TDD128	ControlChannelDRXInfo-TDD128-r8		OPTIONAL,
		sps-Information-TDD128			SPS-Information-TDD128-r8			OPTIONAL,
		maxAllowedUL-TX-Power			MaxAllowedUL-TX-Power				OPTIONAL,
		ul-DPCH-Info					UL-DPCH-Info-r7						OPTIONAL,
		ul-EDCH-Information				UL-EDCH-Information-r9				OPTIONAL,
		ul-SecondaryCellInfoFDD			UL-SecondaryCellInfoFDD				OPTIONAL,
		dl-HSPDSCH-Information			DL-HSPDSCH-Information-r9			OPTIONAL,
		dl-CommonInformation			DL-CommonInformation-r8				OPTIONAL,
		dl-InformationPerRL-List		DL-InformationPerRL-List-r8			OPTIONAL,
		dl-SecondaryCellInfoFDD			DL-SecondaryCellInfoFDD-r9			OPTIONAL,
	-- MBMS IEs
		mbms-PL-ServiceRestrictInfo		MBMS-PL-ServiceRestrictInfo-r6		OPTIONAL,
	-- Measurement IEs for LCR
		cellDCHMeasOccasionInfo-TDD128	CellDCHMeasOccasionInfo-TDD128-r9	OPTIONAL
}

PhysicalChannelReconfiguration-v950ext-IEs ::= SEQUENCE {
	-- Physical channel IEs
		secondaryCellMimoParameters		SecondaryCellMIMOparametersFDD-v950ext		OPTIONAL
}

PhysicalChannelReconfiguration-r10-IEs ::= SEQUENCE {
	-- User equipment IEs
		integrityProtectionModeInfo		IntegrityProtectionModeInfo-r7		OPTIONAL,
		cipheringModeInfo				CipheringModeInfo-r7				OPTIONAL,
		activationTime					ActivationTime						OPTIONAL,
		delayRestrictionFlag			DelayRestrictionFlag				OPTIONAL,
		new-U-RNTI						U-RNTI								OPTIONAL,
		new-C-RNTI						C-RNTI								OPTIONAL,
		-- The IE "new-DSCH-RNTI" should not be included in FDD mode,
		-- and if received the UE behaviour is unspecified
		new-DSCH-RNTI					DSCH-RNTI							OPTIONAL,
		new-H-RNTI						H-RNTI								OPTIONAL,
		newPrimary-E-RNTI				E-RNTI								OPTIONAL,
		newSecondary-E-RNTI				E-RNTI								OPTIONAL,
		rrc-StateIndicator				RRC-StateIndicator,
		ueMobilityStateIndicator		High-MobilityDetected				OPTIONAL,
		utran-DRX-CycleLengthCoeff		UTRAN-DRX-CycleLengthCoefficient-r7	OPTIONAL,
	-- Core network IEs
		cn-InformationInfo				CN-InformationInfo-r6				OPTIONAL,
	-- UTRAN mobility IEs
		ura-Identity					URA-Identity						OPTIONAL,
		supportForChangeOfUE-Capability	BOOLEAN								OPTIONAL,
		responseToChangeOfUE-Capability	ENUMERATED { true }					OPTIONAL,
	-- Radio bearer IEs
		dl-CounterSynchronisationInfo	DL-CounterSynchronisationInfo-r5	OPTIONAL,
	-- Transport channel IEs
		harqInfo						HARQ-Info-r7						OPTIONAL,
	-- Physical channel IEs
		frequencyInfo					FrequencyInfo						OPTIONAL,
		multi-frequencyInfo				Multi-frequencyInfo-LCR-r7			OPTIONAL,
		dtx-drx-TimingInfo				DTX-DRX-TimingInfo-r7				OPTIONAL,
		dtx-drx-Info					DTX-DRX-Info-r7						OPTIONAL,
		hs-scch-LessInfo				HS-SCCH-LessInfo-r7					OPTIONAL,
		mimoParameters					MIMO-Parameters-r9					OPTIONAL,
		controlChannelDRXInfo-TDD128	ControlChannelDRXInfo-TDD128-r8		OPTIONAL,
		sps-Information-TDD128			SPS-Information-TDD128-r8			OPTIONAL,
		maxAllowedUL-TX-Power			MaxAllowedUL-TX-Power				OPTIONAL,
		ul-DPCH-Info					UL-DPCH-Info-r7						OPTIONAL,
		ul-EDCH-Information				UL-EDCH-Information-r9				OPTIONAL,
		ul-SecondaryCellInfoFDD			UL-SecondaryCellInfoFDD				OPTIONAL,
		ul-MulticarrierEDCHInfo-TDD128	UL-MulticarrierEDCHInfo-TDD128		OPTIONAL,
		dl-HSPDSCH-Information			DL-HSPDSCH-Information-r9			OPTIONAL,
		dl-CommonInformation			DL-CommonInformation-r10			OPTIONAL,
		dl-InformationPerRL-List		DL-InformationPerRL-List-r8			OPTIONAL,
		dl-SecondaryCellInfoFDD			DL-SecondaryCellInfoFDD-r10			OPTIONAL,
		additionalDLSecCellInfoListFDD	AdditionalDLSecCellInfoListFDD		OPTIONAL,
		mu-MIMO-Info-TDD128				MU-MIMO-Info-TDD128					OPTIONAL,
	-- MBMS IEs
		mbms-PL-ServiceRestrictInfo		MBMS-PL-ServiceRestrictInfo-r6		OPTIONAL,
	-- Measurement IEs for LCR
		cellDCHMeasOccasionInfo-TDD128	CellDCHMeasOccasionInfo-TDD128-r9	OPTIONAL
}

PhysicalChannelReconfiguration-vb50ext-IEs ::= SEQUENCE {
		ulOLTDInfoFDD						UL-OLTD-InfoFDD			OPTIONAL
}

PhysicalChannelReconfiguration-r11-IEs ::= SEQUENCE {
	-- User equipment IEs
		integrityProtectionModeInfo		IntegrityProtectionModeInfo-r7		OPTIONAL,
		cipheringModeInfo				CipheringModeInfo-r7				OPTIONAL,
		activationTime					ActivationTime						OPTIONAL,
		delayRestrictionFlag			DelayRestrictionFlag				OPTIONAL,
		new-U-RNTI						U-RNTI								OPTIONAL,
		new-C-RNTI						C-RNTI								OPTIONAL,
		-- The IE "new-DSCH-RNTI" should not be included in FDD mode,
		-- and if received the UE behaviour is unspecified
		new-DSCH-RNTI					DSCH-RNTI							OPTIONAL,
		new-H-RNTI						H-RNTI								OPTIONAL,
		newPrimary-E-RNTI				E-RNTI								OPTIONAL,
		newSecondary-E-RNTI				E-RNTI								OPTIONAL,
		rrc-StateIndicator				RRC-StateIndicator,
		ueMobilityStateIndicator		High-MobilityDetected				OPTIONAL,
		utran-DRX-CycleLengthCoeff		UTRAN-DRX-CycleLengthCoefficient-r7	OPTIONAL,
	-- Core network IEs
		cn-InformationInfo				CN-InformationInfo-r6				OPTIONAL,
	-- UTRAN mobility IEs
		ura-Identity					URA-Identity						OPTIONAL,
		supportForChangeOfUE-Capability	BOOLEAN								OPTIONAL,
		responseToChangeOfUE-Capability	ENUMERATED { true }					OPTIONAL,
	-- Radio bearer IEs
		dl-CounterSynchronisationInfo	DL-CounterSynchronisationInfo-r5	OPTIONAL,
	-- Transport channel IEs
		harqInfo						HARQ-Info-r11						OPTIONAL,
	-- Physical channel IEs
		frequencyInfo					FrequencyInfo						OPTIONAL,
		multi-frequencyInfo				Multi-frequencyInfo-LCR-r7			OPTIONAL,
		dtx-drx-TimingInfo				DTX-DRX-TimingInfo-r7				OPTIONAL,
		dtx-drx-Info					DTX-DRX-Info-r7						OPTIONAL,
		hs-scch-LessInfo				HS-SCCH-LessInfo-r7					OPTIONAL,
		mimoParameters					MIMO-Parameters-r9					OPTIONAL,
		mimo4x4Parameters				MIMO4x4-Parameters					OPTIONAL,
		controlChannelDRXInfo-TDD128	ControlChannelDRXInfo-TDD128-r8		OPTIONAL,
		sps-Information-TDD128			SPS-Information-TDD128-r8			OPTIONAL,
		maxAllowedUL-TX-Power			MaxAllowedUL-TX-Power				OPTIONAL,
		ul-DPCH-Info					UL-DPCH-Info-r11						OPTIONAL,
		ul-EDCH-Information				UL-EDCH-Information-r11				OPTIONAL,
		ul-SecondaryCellInfoFDD			UL-SecondaryCellInfoFDD				OPTIONAL,
		ul-MulticarrierEDCHInfo-TDD128	UL-MulticarrierEDCHInfo-TDD128		OPTIONAL,
		ul-CLTD-InfoFDD					UL-CLTD-InfoFDD						OPTIONAL,
		ul-OLTD-InfoFDD					UL-OLTD-InfoFDD						OPTIONAL,
		dl-HSPDSCH-Information			DL-HSPDSCH-Information-r11			OPTIONAL,
		dl-CommonInformation			DL-CommonInformation-r11			OPTIONAL,
		dl-InformationPerRL-List		DL-InformationPerRL-List-r11			OPTIONAL,
		dl-SecondaryCellInfoFDD			DL-SecondaryCellInfoFDD-r11			OPTIONAL,
		additionalDLSecCellInfoListFDD	AdditionalDLSecCellInfoListFDD-r11	OPTIONAL,
		additionalDLSecCellInfoListFDD2 AdditionalDLSecCellInfoListFDD2		OPTIONAL,
		commonERGCHInfoFDD				CommonERGCHInfoFDD					OPTIONAL,
		mu-MIMO-Info-TDD128				MU-MIMO-Info-TDD128					OPTIONAL,
	-- MBMS IEs
		mbms-PL-ServiceRestrictInfo		MBMS-PL-ServiceRestrictInfo-r6		OPTIONAL,
	-- Measurement IEs for LCR
		cellDCHMeasOccasionInfo-TDD128	CellDCHMeasOccasionInfo-TDD128-r9	OPTIONAL
}

-- ***************************************************
--
-- PHYSICAL CHANNEL RECONFIGURATION COMPLETE
--
-- ***************************************************

PhysicalChannelReconfigurationComplete ::= SEQUENCE {
	-- User equipment IEs
		rrc-TransactionIdentifier		RRC-TransactionIdentifier,
		ul-IntegProtActivationInfo		IntegrityProtActivationInfo			OPTIONAL,
		-- TABULAR: UL-TimingAdvance is applicable for TDD mode only.
		ul-TimingAdvance				UL-TimingAdvance					OPTIONAL,
	-- Radio bearer IEs
		count-C-ActivationTime			ActivationTime						OPTIONAL,
		-- dummy is not used in this version of the specification and
		-- it should be ignored by the receiver.
		dummy							RB-ActivationTimeInfoList			OPTIONAL,
		ul-CounterSynchronisationInfo	UL-CounterSynchronisationInfo		OPTIONAL,
		laterNonCriticalExtensions		SEQUENCE {
			-- Container for additional R99 extensions
			physicalChannelReconfigurationComplete-r3-add-ext		BIT STRING		OPTIONAL,
			v770NonCriticalExtensions		SEQUENCE {
				physicalChannelReconfigurationComplete-v770ext
									PhysicalChannelReconfigurationComplete-v770ext-IEs,
				nonCriticalExtensions			SEQUENCE {}		OPTIONAL
			}	OPTIONAL
		}	OPTIONAL
}

PhysicalChannelReconfigurationComplete-v770ext-IEs ::=	SEQUENCE {
		-- TABULAR: EXT-UL-TimingAdvance is applicable for TDD mode only.
		ext-UL-TimingAdvance					EXT-UL-TimingAdvance	OPTIONAL,
		deferredMeasurementControlReading		ENUMERATED { true }		OPTIONAL
}


-- ***************************************************
--
-- PHYSICAL CHANNEL RECONFIGURATION FAILURE
--
-- ***************************************************

PhysicalChannelReconfigurationFailure ::= SEQUENCE {
	-- User equipment IEs
		rrc-TransactionIdentifier		RRC-TransactionIdentifier			OPTIONAL,
		failureCause					FailureCauseWithProtErr,
		laterNonCriticalExtensions		SEQUENCE {
			-- Container for additional R99 extensions
			physicalChannelReconfigurationFailure-r3-add-ext		BIT STRING		OPTIONAL,
			nonCriticalExtensions			SEQUENCE {}		OPTIONAL
		}	OPTIONAL
}

-- ***************************************************
--
-- PHYSICAL SHARED CHANNEL ALLOCATION (TDD only)
--
-- ***************************************************

PhysicalSharedChannelAllocation ::= CHOICE {
	r3								SEQUENCE {
		physicalSharedChannelAllocation-r3
										PhysicalSharedChannelAllocation-r3-IEs,
		laterNonCriticalExtensions		SEQUENCE {
			-- Container for additional R99 extensions
			physicalSharedChannelAllocation-r3-add-ext		BIT STRING		OPTIONAL,
			nonCriticalExtensions			SEQUENCE {}	OPTIONAL
		}	OPTIONAL
	},
	later-than-r3					SEQUENCE {
		dsch-RNTI						DSCH-RNTI							OPTIONAL,
		rrc-TransactionIdentifier		RRC-TransactionIdentifier,
		criticalExtensions				CHOICE {
			r4								SEQUENCE {
				physicalSharedChannelAllocation-r4
												PhysicalSharedChannelAllocation-r4-IEs,
				v4d0NonCriticalExtensions		SEQUENCE {
					-- Container for adding non critical extensions after freezing REL-5
					physicalSharedChannelAllocation-r4-add-ext		BIT STRING		OPTIONAL,
					v690NonCriticalExtensions		SEQUENCE {
						physicalSharedChannelAllocation-v690ext
														PhysicalSharedChannelAllocation-v690ext-IEs,
						v770NonCriticalExtensions		SEQUENCE {
							physicalSharedChannelAllocation-v770ext
														PhysicalSharedChannelAllocation-v770ext-IEs,
							nonCriticalExtensions			SEQUENCE {}		OPTIONAL
						}		OPTIONAL
					}		OPTIONAL
				}		OPTIONAL
			},
			criticalExtensions				SEQUENCE {}
		}
	}
}

PhysicalSharedChannelAllocation-r3-IEs ::= SEQUENCE {
	-- TABULAR: Integrity protection shall not be performed on this message.
	-- User equipment IEs
		dsch-RNTI						DSCH-RNTI							OPTIONAL,
		rrc-TransactionIdentifier		RRC-TransactionIdentifier,
	-- Physical channel IEs
		ul-TimingAdvance				UL-TimingAdvanceControl				OPTIONAL,
		pusch-CapacityAllocationInfo	PUSCH-CapacityAllocationInfo		OPTIONAL,
		pdsch-CapacityAllocationInfo	PDSCH-CapacityAllocationInfo		OPTIONAL,
		-- TABULAR: If confirmRequest is not present, the default value "No Confirm"
		-- shall be used as specified in 10.2.25.		
		confirmRequest					ENUMERATED {
											confirmPDSCH, confirmPUSCH }	OPTIONAL,
		trafficVolumeReportRequest		INTEGER (0..255)					OPTIONAL,	
		iscpTimeslotList					TimeslotList						OPTIONAL,
		requestPCCPCHRSCP					BOOLEAN
}

PhysicalSharedChannelAllocation-r4-IEs ::= SEQUENCE {
	-- TABULAR: Integrity protection shall not be performed on this message.
	-- Physical channel IEs
		ul-TimingAdvance				UL-TimingAdvanceControl-r4			OPTIONAL,
		pusch-CapacityAllocationInfo	PUSCH-CapacityAllocationInfo-r4		OPTIONAL,
		pdsch-CapacityAllocationInfo	PDSCH-CapacityAllocationInfo-r4		OPTIONAL,
		-- TABULAR: If confirmRequest is not present, the default value "No Confirm"
		-- shall be used as specified in 10.2.25.		
		confirmRequest					ENUMERATED {
											confirmPDSCH, confirmPUSCH }	OPTIONAL,
		trafficVolumeReportRequest		INTEGER (0..255)					OPTIONAL,
		iscpTimeslotList				TimeslotList-r4						OPTIONAL,
		requestPCCPCHRSCP				BOOLEAN
}

PhysicalSharedChannelAllocation-v690ext-IEs ::= SEQUENCE {
	-- Physical Channel IEs
		beaconPLEst						BEACON-PL-Est						OPTIONAL
}

PhysicalSharedChannelAllocation-v770ext-IEs ::= SEQUENCE {
		ul-TimingAdvance				UL-TimingAdvanceControl-r7			OPTIONAL,
		pusch-CapacityAllocationInfo	PUSCH-CapacityAllocationInfo-r7		OPTIONAL,
		pdsch-CapacityAllocationInfo	PDSCH-CapacityAllocationInfo-r7		OPTIONAL
}

-- ***************************************************
--
-- PUSCH CAPACITY REQUEST (TDD only)
--
-- ***************************************************

PUSCHCapacityRequest ::= SEQUENCE {
	-- User equipment IEs
		dsch-RNTI						DSCH-RNTI							OPTIONAL,
	-- Measurement IEs
		trafficVolume					TrafficVolumeMeasuredResultsList	OPTIONAL,
		timeslotListWithISCP			TimeslotListWithISCP				OPTIONAL,
		primaryCCPCH-RSCP				PrimaryCCPCH-RSCP					OPTIONAL,
		allocationConfirmation			CHOICE {
			pdschConfirmation				PDSCH-Identity,
			puschConfirmation				PUSCH-Identity
		}																	OPTIONAL,
		protocolErrorIndicator			ProtocolErrorIndicatorWithMoreInfo,
		laterNonCriticalExtensions		SEQUENCE {
			-- Container for additional R99 extensions
			puschCapacityRequest-r3-add-ext		BIT STRING		OPTIONAL,
			v590NonCriticalExtensions		SEQUENCE {
				puschCapacityRequest-v590ext	PUSCHCapacityRequest-v590ext,
				nonCriticalExtensions			SEQUENCE {}	OPTIONAL
			}		OPTIONAL
		}	OPTIONAL
}

PUSCHCapacityRequest-v590ext ::= SEQUENCE {
	primaryCCPCH-RSCP-delta				DeltaRSCP			OPTIONAL
}

-- ***************************************************
--
-- RADIO BEARER RECONFIGURATION
--
-- ***************************************************

RadioBearerReconfiguration ::= CHOICE {
	r3								SEQUENCE {
		radioBearerReconfiguration-r3	RadioBearerReconfiguration-r3-IEs,
		-- Prefix "v3ao" is used (in one instance) to keep alignment with R99
		v3aoNonCriticalExtensions		SEQUENCE {
			radioBearerReconfiguration-v3a0ext	RadioBearerReconfiguration-v3a0ext,
			laterNonCriticalExtensions		SEQUENCE {
				-- Container for additional R99 extensions
				radioBearerReconfiguration-r3-add-ext		BIT STRING		OPTIONAL,
				v4b0NonCriticalExtensions			SEQUENCE {
					radioBearerReconfiguration-v4b0ext	
													RadioBearerReconfiguration-v4b0ext-IEs,
					v590NonCriticalExtensions			SEQUENCE {
						radioBearerReconfiguration-v590ext	
														RadioBearerReconfiguration-v590ext-IEs,
						v5d0NonCriticalExtenstions			SEQUENCE {
							radioBearerReconfiguration-v5d0ext
															RadioBearerReconfiguration-v5d0ext-IEs,
							v690NonCriticalExtensions		SEQUENCE {
								radioBearerReconfiguration-v690ext
															RadioBearerReconfiguration-v690ext-IEs,
								v770NonCriticalExtensions		SEQUENCE {
									radioBearerReconfiguration-v770ext
															RadioBearerReconfiguration-v770ext-IEs,
									nonCriticalExtensions			SEQUENCE {} OPTIONAL
								}	OPTIONAL
							}	OPTIONAL
						}	OPTIONAL
					}	OPTIONAL
				}	OPTIONAL
			}	OPTIONAL
		}	OPTIONAL
	},
	later-than-r3					SEQUENCE {
		rrc-TransactionIdentifier		RRC-TransactionIdentifier,
		criticalExtensions				CHOICE {
			r4								SEQUENCE {
				radioBearerReconfiguration-r4	RadioBearerReconfiguration-r4-IEs,
				v4d0NonCriticalExtensions			SEQUENCE {
					-- Container for adding non critical extensions after freezing REL-5
					radioBearerReconfiguration-r4-add-ext		BIT STRING		OPTIONAL,
					v590NonCriticalExtensions			SEQUENCE {
						radioBearerReconfiguration-v590ext	
													RadioBearerReconfiguration-v590ext-IEs,
						v5d0NonCriticalExtenstions			SEQUENCE {
							radioBearerReconfiguration-v5d0ext
															RadioBearerReconfiguration-v5d0ext-IEs,
							v690NonCriticalExtensions		SEQUENCE {
								radioBearerReconfiguration-v690ext
															RadioBearerReconfiguration-v690ext-IEs,
								v770NonCriticalExtensions		SEQUENCE {
									radioBearerReconfiguration-v770ext
															RadioBearerReconfiguration-v770ext-IEs,
									nonCriticalExtensions			SEQUENCE {}		OPTIONAL
								}	OPTIONAL
							}	OPTIONAL
						}	OPTIONAL
					}	OPTIONAL
				}	OPTIONAL
			},
			criticalExtensions				CHOICE {
				r5									SEQUENCE {
					radioBearerReconfiguration-r5		RadioBearerReconfiguration-r5-IEs,
					-- Container for adding non critical extensions after freezing REL-6
					radioBearerReconfiguration-r5-add-ext		BIT STRING		OPTIONAL,
					v5d0NonCriticalExtenstions			SEQUENCE {
						radioBearerReconfiguration-v5d0ext	RadioBearerReconfiguration-v5d0ext-IEs,
						v690NonCriticalExtensions			SEQUENCE {
							radioBearerReconfiguration-v690ext
															RadioBearerReconfiguration-v690ext-IEs,
							v770NonCriticalExtensions			SEQUENCE {
								radioBearerReconfiguration-v770ext
															RadioBearerReconfiguration-v770ext-IEs,
								nonCriticalExtensions				SEQUENCE {}		OPTIONAL
							}	OPTIONAL
						}	OPTIONAL
					}	OPTIONAL
				},
				criticalExtensions				CHOICE {
					r6									SEQUENCE {
						radioBearerReconfiguration-r6		RadioBearerReconfiguration-r6-IEs,
						-- Container for adding non critical extensions after freezing REL-7
						radioBearerReconfiguration-r6-add-ext		BIT STRING		OPTIONAL,
						v6b0NonCriticalExtensions			SEQUENCE {
							radioBearerReconfiguration-v6b0ext
															RadioBearerReconfiguration-v6b0ext-IEs,
							v6f0NonCriticalExtensions			SEQUENCE {
								radioBearerRconfiguration-v6f0ext
															RadioBearerReconfiguration-v6f0ext-IEs,
								v770NonCriticalExtensions			SEQUENCE {
									radioBearerReconfiguration-v770ext
															RadioBearerReconfiguration-v770ext-IEs,
									nonCriticalExtensions				SEQUENCE {}		OPTIONAL
								}	OPTIONAL
							}	OPTIONAL
						}	OPTIONAL
					},
					criticalExtensions				CHOICE {
						r7									SEQUENCE {
							radioBearerReconfiguration-r7		RadioBearerReconfiguration-r7-IEs,
							v780NonCriticalExtensions		SEQUENCE {
								radioBearerReconfiguration-v780ext
															RadioBearerReconfiguration-v780ext-IEs,
								v790NonCriticalExtensions		SEQUENCE {
									radioBearerReconfiguration-v790ext
															RadioBearerReconfiguration-v790ext-IEs,
									v7d0NonCriticalExtensions		SEQUENCE {
										radioBearerReconfiguration-v7d0ext
															RadioBearerReconfiguration-v7d0ext-IEs,
										v7f0NonCriticalExtensions		SEQUENCE {
											radioBearerReconfiguration-v7f0ext
															RadioBearerReconfiguration-v7f0ext-IEs,
											v7g0NonCriticalExtensions		SEQUENCE {
												radioBearerReconfiguration-v7g0ext
															RadioBearerReconfiguration-v7g0ext-IEs,
												nonCriticalExtensions		SEQUENCE {}		OPTIONAL
											}	OPTIONAL
										}	OPTIONAL
									}	OPTIONAL
								}	OPTIONAL
							}	OPTIONAL
						},
						criticalExtensions				CHOICE {
							r8								SEQUENCE {
								radioBearerReconfiguration-r8	RadioBearerReconfiguration-r8-IEs,
								-- Container for adding non critical extensions after freezing REL-9
								radioBearerReconfiguration-r8-add-ext	BIT STRING		OPTIONAL,
								v7d0NonCriticalExtensions		SEQUENCE {
									radioBearerReconfiguration-v7d0ext
															RadioBearerReconfiguration-v7d0ext-IEs,
									v7f0NonCriticalExtensions		SEQUENCE {
										radioBearerReconfiguration-v7f0ext
															RadioBearerReconfiguration-v7f0ext-IEs,
										v890NonCriticalExtensions		SEQUENCE {
											radioBearerReconfiguration-v890ext
															RadioBearerReconfiguration-v890ext-IEs,
											v7g0NonCriticalExtensions		SEQUENCE {
												radioBearerReconfiguration-v7g0ext
															RadioBearerReconfiguration-v7g0ext-IEs,
												v8a0NonCriticalExtensions		SEQUENCE {
													radioBearerReconfiguration-v8a0ext
															RadioBearerReconfiguration-v8a0ext-IEs,
													nonCriticalExtensions		SEQUENCE {}		OPTIONAL
												}	OPTIONAL
											}	OPTIONAL
										}	OPTIONAL
									}	OPTIONAL
								}	OPTIONAL
							},
							criticalExtensions				CHOICE {
								r9								SEQUENCE {
									radioBearerReconfiguration-r9
																RadioBearerReconfiguration-r9-IEs,
									-- Container for adding non critical extensions after 
									-- freezing REL-10
									radioBearerReconfiguration-r9-add-ext
																	BIT STRING		OPTIONAL,
									v950NonCriticalExtensions		SEQUENCE {
										radioBearerReconfiguration-v950ext	
															RadioBearerReconfiguration-v950ext-IEs,
										v9c0NonCriticalExtensions		SEQUENCE {
											radioBearerReconfiguration-v9c0ext	
															RadioBearerReconfiguration-v9c0ext-IEs,
											nonCriticalExtensions			SEQUENCE {}		OPTIONAL
										}	OPTIONAL
									}	OPTIONAL
								},
								criticalExtensions				CHOICE {
									r10								SEQUENCE {
										radioBearerReconfiguration-r10
																RadioBearerReconfiguration-r10-IEs,
										-- Container for adding non critical extensions after 
										-- freezing REL-11
										radioBearerReconfiguration-r10-add-ext
																		BIT STRING		OPTIONAL,
										v9c0NonCriticalExtensions		SEQUENCE {
											radioBearerReconfiguration-v9c0ext	
															RadioBearerReconfiguration-v9c0ext-IEs,
											vaa0NonCriticalExtensions		SEQUENCE {
												radioBearerReconfiguration-vaa0ext
															RadioBearerReconfiguration-vaa0ext-IEs,
												vb50NonCriticalExtensions		SEQUENCE {
													radioBearerReconfiguration-vb50ext
															RadioBearerReconfiguration-vb50ext-IEs,
													nonCriticalExtensions	SEQUENCE {}		OPTIONAL
												}	OPTIONAL
											}	OPTIONAL
										}	OPTIONAL
									},
									criticalExtensions				CHOICE {
										r11								SEQUENCE {
											radioBearerReconfiguration-r11
																RadioBearerReconfiguration-r11-IEs,
											-- Container for adding non critical extensions after 
											-- freezing REL-12
											radioBearerReconfiguration-r11-add-ext
																		BIT STRING		OPTIONAL,
											nonCriticalExtensions		SEQUENCE {}		OPTIONAL
										},
										criticalExtensions				SEQUENCE {}
									}
								}
							}
						}
					}
				}
			}
		}
	}
}

RadioBearerReconfiguration-vaa0ext-IEs	::=	SEQUENCE	{
	um-RLC-ReEstablishmentRBList		RB-IdentityList					OPTIONAL
}

RadioBearerReconfiguration-r3-IEs ::= SEQUENCE {
	-- User equipment IEs
		rrc-TransactionIdentifier		RRC-TransactionIdentifier,
		integrityProtectionModeInfo		IntegrityProtectionModeInfo			OPTIONAL,
		cipheringModeInfo				CipheringModeInfo					OPTIONAL,
		activationTime					ActivationTime						OPTIONAL,
		new-U-RNTI						U-RNTI								OPTIONAL,
		new-C-RNTI						C-RNTI								OPTIONAL,
		rrc-StateIndicator				RRC-StateIndicator,
		utran-DRX-CycleLengthCoeff		UTRAN-DRX-CycleLengthCoefficient	OPTIONAL,
	-- Core network IEs
		cn-InformationInfo				CN-InformationInfo					OPTIONAL,
	-- UTRAN mobility IEs
		ura-Identity					URA-Identity						OPTIONAL,
	-- Radio bearer IEs
		rab-InformationReconfigList		RAB-InformationReconfigList			OPTIONAL,
		-- NOTE: IE rb-InformationReconfigList should be optional in later versions
		-- of this message
		rb-InformationReconfigList		RB-InformationReconfigList,
		rb-InformationAffectedList		RB-InformationAffectedList			OPTIONAL,
	-- Transport channel IEs
		ul-CommonTransChInfo			UL-CommonTransChInfo				OPTIONAL,
		ul-deletedTransChInfoList		UL-DeletedTransChInfoList			OPTIONAL,
		ul-AddReconfTransChInfoList		UL-AddReconfTransChInfoList			OPTIONAL,
		-- 'dummy', 'dummy1' and 'dummy2' are not used in this version of the specification,
		-- they should not be sent and if received they should be ignored.
		dummy							CHOICE {
			fdd								SEQUENCE {
				dummy1							CPCH-SetID					OPTIONAL,
				dummy2							DRAC-StaticInformationList	OPTIONAL
			},
			tdd								NULL
		}																	OPTIONAL,
		dl-CommonTransChInfo			DL-CommonTransChInfo				OPTIONAL,
		dl-DeletedTransChInfoList		DL-DeletedTransChInfoList			OPTIONAL,
		dl-AddReconfTransChInfoList		DL-AddReconfTransChInfo2List		OPTIONAL,
	-- Physical channel IEs
		frequencyInfo					FrequencyInfo						OPTIONAL,
		maxAllowedUL-TX-Power			MaxAllowedUL-TX-Power				OPTIONAL,
		ul-ChannelRequirement			UL-ChannelRequirement				OPTIONAL,
		modeSpecificPhysChInfo			CHOICE {
			fdd								SEQUENCE {
				-- dummy is not used in this version of specification, it should
				-- not be sent and if received it should be ignored.
				dummy							DL-PDSCH-Information		OPTIONAL
			},
			tdd								NULL
		},
		dl-CommonInformation			DL-CommonInformation				OPTIONAL,
		-- NOTE: IE dl-InformationPerRL-List is optional in later versions
		-- of this message
		dl-InformationPerRL-List		DL-InformationPerRL-List
}

RadioBearerReconfiguration-v3a0ext ::= SEQUENCE {
	-- The IE "new-DSCH-RNTI" should not be included in FDD mode, and if received the UE behaviour
	-- is unspecified
	new-DSCH-RNTI					DSCH-RNTI							OPTIONAL
}

RadioBearerReconfiguration-v4b0ext-IEs ::= SEQUENCE {
	-- Physical channel IEs
		-- dummy is not used in this version of the specification, it should
		-- not be sent and if received it should be ignored.
		dummy								SSDT-UL								OPTIONAL,
		-- The order of the RLs in IE cell-id-PerRL-List is the same as
		-- in IE DL-InformationPerRL-List included in this message
		cell-id-PerRL-List					CellIdentity-PerRL-List				OPTIONAL
}

RadioBearerReconfiguration-v590ext-IEs ::= SEQUENCE {
	-- Physical channel IEs
		dl-TPC-PowerOffsetPerRL-List	DL-TPC-PowerOffsetPerRL-List		OPTIONAL
}

RadioBearerReconfiguration-v5d0ext-IEs ::= SEQUENCE {
	--Radio Bearer IEs
		pdcp-ROHC-TargetMode			PDCP-ROHC-TargetMode				OPTIONAL
}

RadioBearerReconfiguration-r4-IEs ::= SEQUENCE {
	-- User equipment IEs
		integrityProtectionModeInfo		IntegrityProtectionModeInfo			OPTIONAL,
		cipheringModeInfo				CipheringModeInfo					OPTIONAL,
		activationTime					ActivationTime						OPTIONAL,
		new-U-RNTI						U-RNTI								OPTIONAL,
		new-C-RNTI						C-RNTI								OPTIONAL,
		-- The IE "new-DSCH-RNTI" should not be included in FDD mode, and if received
		-- the UE behaviour is unspecified
		new-DSCH-RNTI					DSCH-RNTI							OPTIONAL,
		rrc-StateIndicator				RRC-StateIndicator,
		utran-DRX-CycleLengthCoeff		UTRAN-DRX-CycleLengthCoefficient	OPTIONAL,
	-- Core network IEs
		cn-InformationInfo				CN-InformationInfo					OPTIONAL,
	-- UTRAN mobility IEs
		ura-Identity					URA-Identity						OPTIONAL,
	-- Radio bearer IEs
		rab-InformationReconfigList		RAB-InformationReconfigList			OPTIONAL,
		rb-InformationReconfigList		RB-InformationReconfigList-r4		OPTIONAL,
		rb-InformationAffectedList		RB-InformationAffectedList			OPTIONAL,
	-- Transport channel IEs
		ul-CommonTransChInfo			UL-CommonTransChInfo-r4				OPTIONAL,
		ul-deletedTransChInfoList		UL-DeletedTransChInfoList			OPTIONAL,
		ul-AddReconfTransChInfoList		UL-AddReconfTransChInfoList			OPTIONAL,
		-- 'dummy', 'dummy1' and 'dummy2' are not used in this version of the specification,
		-- they should not be sent and if received they should be ignored.
		dummy							CHOICE {
			fdd								SEQUENCE {
				dummy1							CPCH-SetID					OPTIONAL,
				dummy2							DRAC-StaticInformationList	OPTIONAL
			},
			tdd								NULL
		}																	OPTIONAL,
		dl-CommonTransChInfo			DL-CommonTransChInfo-r4				OPTIONAL,
		dl-DeletedTransChInfoList		DL-DeletedTransChInfoList			OPTIONAL,
		dl-AddReconfTransChInfoList		DL-AddReconfTransChInfoList-r4		OPTIONAL,
	-- Physical channel IEs
		frequencyInfo					FrequencyInfo						OPTIONAL,
		maxAllowedUL-TX-Power			MaxAllowedUL-TX-Power				OPTIONAL,
		ul-ChannelRequirement			UL-ChannelRequirement-r4			OPTIONAL,
		modeSpecificPhysChInfo			CHOICE {
			fdd								SEQUENCE {
				-- dummy is not used in this version of specification, it should
				-- not be sent and if received it should be ignored.
				dummy							DL-PDSCH-Information		OPTIONAL
			},
			tdd								NULL
		},
		dl-CommonInformation			DL-CommonInformation-r4				OPTIONAL,
		dl-InformationPerRL-List		DL-InformationPerRL-List-r4 		OPTIONAL
}

RadioBearerReconfiguration-r5-IEs ::= SEQUENCE {
	-- User equipment IEs
		integrityProtectionModeInfo		IntegrityProtectionModeInfo			OPTIONAL,
		cipheringModeInfo				CipheringModeInfo					OPTIONAL,
		activationTime					ActivationTime						OPTIONAL,
		new-U-RNTI						U-RNTI								OPTIONAL,
		new-C-RNTI						C-RNTI								OPTIONAL,
		-- The IE "new-DSCH-RNTI" should not be included in FDD mode, and if received 
		-- the UE behaviour is unspecified
		new-DSCH-RNTI					DSCH-RNTI							OPTIONAL,
		new-H-RNTI						H-RNTI								OPTIONAL,
		rrc-StateIndicator				RRC-StateIndicator,
		utran-DRX-CycleLengthCoeff		UTRAN-DRX-CycleLengthCoefficient	OPTIONAL,
	-- Core network IEs
		cn-InformationInfo				CN-InformationInfo					OPTIONAL,
	-- UTRAN mobility IEs
		ura-Identity					URA-Identity						OPTIONAL,
	-- Specification mode information
		specificationMode				CHOICE {
			complete						SEQUENCE {
			-- Radio bearer IEs
				rab-InformationReconfigList		RAB-InformationReconfigList			OPTIONAL,
				rb-InformationReconfigList		RB-InformationReconfigList-r5		OPTIONAL,
				rb-InformationAffectedList		RB-InformationAffectedList-r5		OPTIONAL,
				rb-PDCPContextRelocationList	RB-PDCPContextRelocationList		OPTIONAL,
			-- Transport channel IEs
				ul-CommonTransChInfo			UL-CommonTransChInfo-r4				OPTIONAL,
				ul-deletedTransChInfoList		UL-DeletedTransChInfoList			OPTIONAL,
				ul-AddReconfTransChInfoList		UL-AddReconfTransChInfoList			OPTIONAL,
				-- 'dummy', 'dummy1' and 'dummy2' are not used in this version of the
				-- specification, they should not be sent and if received they should be ignored.
				dummy							CHOICE {
					fdd								SEQUENCE {
						dummy1							CPCH-SetID					OPTIONAL,
						dummy2							DRAC-StaticInformationList	OPTIONAL
					},
					tdd								NULL
				}																	OPTIONAL,
				dl-CommonTransChInfo			DL-CommonTransChInfo-r4				OPTIONAL,
				dl-DeletedTransChInfoList		DL-DeletedTransChInfoList-r5		OPTIONAL,
				dl-AddReconfTransChInfoList		DL-AddReconfTransChInfoList-r5		OPTIONAL
			},
			preconfiguration				SEQUENCE {
			-- All IEs that include an FDD/TDD choice are split in two IEs for this message,
			-- one for the FDD only elements and one for the TDD only elements, so that one
			-- FDD/TDD choice in this level is sufficient.
				preConfigMode					CHOICE {
					predefinedConfigIdentity		PredefinedConfigIdentity,
					defaultConfig					SEQUENCE {
						defaultConfigMode				DefaultConfigMode,
						defaultConfigIdentity 			DefaultConfigIdentity-r5
					}
				}
			}
		},
	-- Physical channel IEs
		frequencyInfo					FrequencyInfo						OPTIONAL,
		maxAllowedUL-TX-Power			MaxAllowedUL-TX-Power				OPTIONAL,
		ul-ChannelRequirement			UL-ChannelRequirement-r5			OPTIONAL,
		modeSpecificPhysChInfo			CHOICE {
			fdd								SEQUENCE {
				-- dummy is not used in this version of specification, it should
				-- not be sent and if received it should be ignored.
				dummy							DL-PDSCH-Information		OPTIONAL
			},
			tdd								NULL
		},
		dl-HSPDSCH-Information			DL-HSPDSCH-Information				OPTIONAL,
		dl-CommonInformation			DL-CommonInformation-r5				OPTIONAL,
		dl-InformationPerRL-List		DL-InformationPerRL-List-r5 		OPTIONAL
}

RadioBearerReconfiguration-r6-IEs ::= SEQUENCE {
	-- User equipment IEs
		integrityProtectionModeInfo		IntegrityProtectionModeInfo			OPTIONAL,
		cipheringModeInfo				CipheringModeInfo					OPTIONAL,
		activationTime					ActivationTime						OPTIONAL,
		delayRestrictionFlag			DelayRestrictionFlag				OPTIONAL,
		new-U-RNTI						U-RNTI								OPTIONAL,
		new-C-RNTI						C-RNTI								OPTIONAL,
		-- The IE "new-DSCH-RNTI" should not be included in FDD mode,
		-- and if received the UE behaviour is unspecified
		new-DSCH-RNTI					DSCH-RNTI							OPTIONAL,
		new-H-RNTI						H-RNTI								OPTIONAL,
		newPrimary-E-RNTI				E-RNTI								OPTIONAL,
		newSecondary-E-RNTI				E-RNTI								OPTIONAL,
		rrc-StateIndicator				RRC-StateIndicator,
		utran-DRX-CycleLengthCoeff		UTRAN-DRX-CycleLengthCoefficient	OPTIONAL,
	-- Core network IEs
		cn-InformationInfo				CN-InformationInfo-r6				OPTIONAL,
	-- UTRAN mobility IEs
		ura-Identity					URA-Identity						OPTIONAL,
	-- Specification mode information
		specificationMode				CHOICE {
			complete						SEQUENCE {
			-- Radio bearer IEs
				rab-InformationReconfigList		RAB-InformationReconfigList			OPTIONAL,
				rb-InformationReconfigList		RB-InformationReconfigList-r6		OPTIONAL,
				rb-InformationAffectedList		RB-InformationAffectedList-r6		OPTIONAL,
				rb-PDCPContextRelocationList	RB-PDCPContextRelocationList		OPTIONAL,
				pdcp-ROHC-TargetMode			PDCP-ROHC-TargetMode				OPTIONAL,
			-- Transport channel IEs
				ul-CommonTransChInfo			UL-CommonTransChInfo-r4				OPTIONAL,
				ul-deletedTransChInfoList		UL-DeletedTransChInfoList-r6		OPTIONAL,
				ul-AddReconfTransChInfoList		UL-AddReconfTransChInfoList-r6		OPTIONAL,
				dl-CommonTransChInfo			DL-CommonTransChInfo-r4				OPTIONAL,
				dl-DeletedTransChInfoList		DL-DeletedTransChInfoList-r5		OPTIONAL,
				dl-AddReconfTransChInfoList		DL-AddReconfTransChInfoList-r5		OPTIONAL
			},
			preconfiguration				SEQUENCE {
			-- All IEs that include an FDD/TDD choice are split in two IEs for this message,
			-- one for the FDD only elements and one for the TDD only elements, so that one
			-- FDD/TDD choice in this level is sufficient.
				preConfigMode					CHOICE {
					predefinedConfigIdentity		PredefinedConfigIdentity,
					defaultConfig					SEQUENCE {
						defaultConfigMode				DefaultConfigMode,
						defaultConfigIdentity 			DefaultConfigIdentity-r6
					}
				}
			}
		},
	-- Physical channel IEs
		frequencyInfo					FrequencyInfo						OPTIONAL,
		maxAllowedUL-TX-Power			MaxAllowedUL-TX-Power				OPTIONAL,
		ul-DPCH-Info					UL-DPCH-Info-r6						OPTIONAL,
		ul-EDCH-Information				UL-EDCH-Information-r6				OPTIONAL,
		dl-HSPDSCH-Information			DL-HSPDSCH-Information-r6			OPTIONAL,
		dl-CommonInformation			DL-CommonInformation-r6				OPTIONAL,
		dl-InformationPerRL-List		DL-InformationPerRL-List-r6			OPTIONAL,
	-- MBMS IEs
		mbms-PL-ServiceRestrictInfo		MBMS-PL-ServiceRestrictInfo-r6		OPTIONAL
}

RadioBearerReconfiguration-v690ext-IEs ::= SEQUENCE {
	-- User Equipment IEs
		delayRestrictionFlag			DelayRestrictionFlag				OPTIONAL,
	-- Core network IEs
		primary-plmn-Identity			PLMN-Identity						OPTIONAL,
	-- Physical channel IEs
		-- The IE harq-Preamble-Mode should not be used in the r3 and r4 versions of the message
		-- If included in the r3 or r4 version of the message, the UE should ignore the IE
		harq-Preamble-Mode				HARQ-Preamble-Mode					OPTIONAL,
		beaconPLEst						BEACON-PL-Est						OPTIONAL,
		postVerificationPeriod			ENUMERATED { true }					OPTIONAL,
		dhs-sync						DHS-Sync							OPTIONAL,
		timingMaintainedSynchInd		TimingMaintainedSynchInd			OPTIONAL,
	-- MBMS IEs
		mbms-PL-ServiceRestrictInfo		MBMS-PL-ServiceRestrictInfo-r6		OPTIONAL
}

RadioBearerReconfiguration-v6b0ext-IEs ::= SEQUENCE {
	-- Physical channel IEs
		dl-InformationPerRL-List-v6b0ext	DL-InformationPerRL-List-v6b0ext	OPTIONAL
}

RadioBearerReconfiguration-v6f0ext-IEs ::= SEQUENCE {
	-- Specification mode information
		specificationMode				CHOICE {
			complete						SEQUENCE {
			-- Radio bearer IEs
				rab-InformationMBMSPtpList		RAB-InformationMBMSPtpList			OPTIONAL
			}
		}
}

RadioBearerReconfiguration-r7-IEs ::= SEQUENCE {
	-- User equipment IEs
		integrityProtectionModeInfo		IntegrityProtectionModeInfo-r7		OPTIONAL,
		cipheringModeInfo				CipheringModeInfo-r7				OPTIONAL,
		activationTime					ActivationTime						OPTIONAL,
		delayRestrictionFlag			DelayRestrictionFlag				OPTIONAL,
		new-U-RNTI						U-RNTI								OPTIONAL,
		new-C-RNTI						C-RNTI								OPTIONAL,
		-- The IE "new-DSCH-RNTI" should not be included in FDD mode,
		-- and if received the UE behaviour is unspecified
		new-DSCH-RNTI					DSCH-RNTI							OPTIONAL,
		new-H-RNTI						H-RNTI								OPTIONAL,
		newPrimary-E-RNTI				E-RNTI								OPTIONAL,
		newSecondary-E-RNTI				E-RNTI								OPTIONAL,
		rrc-StateIndicator				RRC-StateIndicator,
		ueMobilityStateIndicator		High-MobilityDetected				OPTIONAL,
		utran-DRX-CycleLengthCoeff		UTRAN-DRX-CycleLengthCoefficient-r7	OPTIONAL,
	-- Core network IEs
		cn-InformationInfo				CN-InformationInfo-r6				OPTIONAL,
	-- UTRAN mobility IEs
		ura-Identity					URA-Identity						OPTIONAL,
		supportForChangeOfUE-Capability	BOOLEAN								OPTIONAL,
		responseToChangeOfUE-Capability	ENUMERATED { true }					OPTIONAL,
	-- Specification mode information
		specificationMode				CHOICE {
			complete						SEQUENCE {
			-- Radio bearer IEs
				rab-InformationReconfigList		RAB-InformationReconfigList			OPTIONAL,
				rab-InformationMBMSPtpList		RAB-InformationMBMSPtpList			OPTIONAL,
				rb-InformationReconfigList		RB-InformationReconfigList-r7		OPTIONAL,
				rb-InformationAffectedList		RB-InformationAffectedList-r7		OPTIONAL,
				rb-PDCPContextRelocationList	RB-PDCPContextRelocationList		OPTIONAL,
				pdcp-ROHC-TargetMode			PDCP-ROHC-TargetMode				OPTIONAL,
			-- Transport channel IEs
				ul-CommonTransChInfo			UL-CommonTransChInfo-r4				OPTIONAL,
				ul-deletedTransChInfoList		UL-DeletedTransChInfoList-r6		OPTIONAL,
				ul-AddReconfTransChInfoList		UL-AddReconfTransChInfoList-r7		OPTIONAL,
				dl-CommonTransChInfo			DL-CommonTransChInfo-r4				OPTIONAL,
				dl-DeletedTransChInfoList		DL-DeletedTransChInfoList-r7		OPTIONAL,
				dl-AddReconfTransChInfoList		DL-AddReconfTransChInfoList-r7		OPTIONAL
			},
			preconfiguration				SEQUENCE {
			-- All IEs that include an FDD/TDD choice are split in two IEs for this message,
			-- one for the FDD only elements and one for the TDD only elements, so that one
			-- FDD/TDD choice in this level is sufficient.
				preConfigMode					CHOICE {
					predefinedConfigIdentity		PredefinedConfigIdentity,
					defaultConfig					SEQUENCE {
						defaultConfigMode				DefaultConfigMode,
						defaultConfigIdentity 			DefaultConfigIdentity-r6
					}
				}
			}
		},
	-- Physical channel IEs
		frequencyInfo					FrequencyInfo						OPTIONAL,
		multi-frequencyInfo				Multi-frequencyInfo-LCR-r7			OPTIONAL,
		dtx-drx-TimingInfo				DTX-DRX-TimingInfo-r7				OPTIONAL,
		dtx-drx-Info					DTX-DRX-Info-r7						OPTIONAL,
		hs-scch-LessInfo				HS-SCCH-LessInfo-r7					OPTIONAL,
		mimoParameters					MIMO-Parameters-r7					OPTIONAL,
		maxAllowedUL-TX-Power			MaxAllowedUL-TX-Power				OPTIONAL,
		ul-DPCH-Info					UL-DPCH-Info-r7						OPTIONAL,
		ul-EDCH-Information				UL-EDCH-Information-r7				OPTIONAL,
		dl-HSPDSCH-Information			DL-HSPDSCH-Information-r7			OPTIONAL,
		dl-CommonInformation			DL-CommonInformation-r7				OPTIONAL,
		dl-InformationPerRL-List		DL-InformationPerRL-List-r7			OPTIONAL,
	-- MBMS IEs
		mbms-PL-ServiceRestrictInfo		MBMS-PL-ServiceRestrictInfo-r6		OPTIONAL
}

RadioBearerReconfiguration-v770ext-IEs ::= SEQUENCE {
	-- User equipment IEs
		ueMobilityStateIndicator		High-MobilityDetected				OPTIONAL
}

RadioBearerReconfiguration-v780ext-IEs ::= SEQUENCE {
	-- Physical channel IEs
		hs-DSCH-TBSizeTable				HS-DSCH-TBSizeTable					OPTIONAL
}

RadioBearerReconfiguration-v790ext-IEs ::= SEQUENCE {
	-- Container for adding non critical extensions after freezing REL-8
		radioBearerReconfiguration-r7-add-ext		BIT STRING				OPTIONAL
}

RadioBearerReconfiguration-v7d0ext-IEs ::= SEQUENCE {
	-- Physical channel IEs
		ul-EDCH-Information				UL-EDCH-Information-ext				OPTIONAL
}

RadioBearerReconfiguration-v7f0ext-IEs ::= SEQUENCE {
	-- Physical channel IEs
	mimoParameters						MIMO-Parameters-v7f0ext				OPTIONAL
}

RadioBearerReconfiguration-v7g0ext-IEs ::= SEQUENCE {
	-- Physical channel IEs
	mimoParameters						MIMO-Parameters-v7g0ext				OPTIONAL
}

RadioBearerReconfiguration-r8-IEs ::= SEQUENCE {
	-- User equipment IEs
		integrityProtectionModeInfo		IntegrityProtectionModeInfo-r7		OPTIONAL,
		cipheringModeInfo				CipheringModeInfo-r7				OPTIONAL,
		activationTime					ActivationTime						OPTIONAL,
		delayRestrictionFlag			DelayRestrictionFlag				OPTIONAL,
		new-U-RNTI						U-RNTI								OPTIONAL,
		new-C-RNTI						C-RNTI								OPTIONAL,
		-- The IE "new-DSCH-RNTI" should not be included in FDD mode,
		-- and if received the UE behaviour is unspecified
		new-DSCH-RNTI					DSCH-RNTI							OPTIONAL,
		new-H-RNTI						H-RNTI								OPTIONAL,
		newPrimary-E-RNTI				E-RNTI								OPTIONAL,
		newSecondary-E-RNTI				E-RNTI								OPTIONAL,
		rrc-StateIndicator				RRC-StateIndicator,
		ueMobilityStateIndicator		High-MobilityDetected				OPTIONAL,
		utran-DRX-CycleLengthCoeff		UTRAN-DRX-CycleLengthCoefficient-r7	OPTIONAL,
	-- Core network IEs
		cn-InformationInfo				CN-InformationInfo-r6				OPTIONAL,
	-- UTRAN mobility IEs
		ura-Identity					URA-Identity						OPTIONAL,
		supportForChangeOfUE-Capability	BOOLEAN								OPTIONAL,
		responseToChangeOfUE-Capability	ENUMERATED { true }					OPTIONAL,
	-- Specification mode information
		-- dummy is not used in this version of the specification, it should
		-- not be sent and if received it should be ignored.
		dummy							DefaultConfigForCellFACH			OPTIONAL,
		specificationMode				CHOICE {
			complete						SEQUENCE {
			-- Radio bearer IEs
				rab-InformationReconfigList		RAB-InformationReconfigList-r8		OPTIONAL,
				rab-InformationMBMSPtpList		RAB-InformationMBMSPtpList			OPTIONAL,
				rb-InformationReconfigList		RB-InformationReconfigList-r8		OPTIONAL,
				rb-InformationAffectedList		RB-InformationAffectedList-r8		OPTIONAL,
				rb-PDCPContextRelocationList	RB-PDCPContextRelocationList		OPTIONAL,
				pdcp-ROHC-TargetMode			PDCP-ROHC-TargetMode				OPTIONAL,
			-- Transport channel IEs
				ul-CommonTransChInfo			UL-CommonTransChInfo-r4				OPTIONAL,
				ul-deletedTransChInfoList		UL-DeletedTransChInfoList-r6		OPTIONAL,
				ul-AddReconfTransChInfoList		UL-AddReconfTransChInfoList-r8		OPTIONAL,
				dl-CommonTransChInfo			DL-CommonTransChInfo-r4				OPTIONAL,
				dl-DeletedTransChInfoList		DL-DeletedTransChInfoList-r7		OPTIONAL,
				dl-AddReconfTransChInfoList		DL-AddReconfTransChInfoList-r7		OPTIONAL
			},
			preconfiguration				SEQUENCE {
			-- All IEs that include an FDD/TDD choice are split in two IEs for this message,
			-- one for the FDD only elements and one for the TDD only elements, so that one
			-- FDD/TDD choice in this level is sufficient.
				preConfigMode					CHOICE {
					predefinedConfigIdentity		PredefinedConfigIdentity,
					defaultConfig					SEQUENCE {
						defaultConfigMode				DefaultConfigMode,
						defaultConfigIdentity 			DefaultConfigIdentity-r6
					}
				}
			}
		},
	-- Physical channel IEs
		frequencyInfo					FrequencyInfo						OPTIONAL,
		multi-frequencyInfo				Multi-frequencyInfo-LCR-r7			OPTIONAL,
		dtx-drx-TimingInfo				DTX-DRX-TimingInfo-r7				OPTIONAL,
		dtx-drx-Info					DTX-DRX-Info-r7						OPTIONAL,
		hs-scch-LessInfo				HS-SCCH-LessInfo-r7					OPTIONAL,
		mimoParameters					MIMO-Parameters-r8					OPTIONAL,
		maxAllowedUL-TX-Power			MaxAllowedUL-TX-Power				OPTIONAL,
		ul-DPCH-Info					UL-DPCH-Info-r7						OPTIONAL,
		ul-EDCH-Information				UL-EDCH-Information-r8				OPTIONAL,
		dl-HSPDSCH-Information			DL-HSPDSCH-Information-r8			OPTIONAL,
		dl-CommonInformation			DL-CommonInformation-r8				OPTIONAL,
		dl-InformationPerRL-List		DL-InformationPerRL-List-r8			OPTIONAL,
		dl-SecondaryCellInfoFDD			DL-SecondaryCellInfoFDD				OPTIONAL,
		controlChannelDRXInfo-TDD128	ControlChannelDRXInfo-TDD128-r8		OPTIONAL,
		sps-Information-TDD128			SPS-Information-TDD128-r8			OPTIONAL,
	-- MBMS IEs
		mbms-PL-ServiceRestrictInfo		MBMS-PL-ServiceRestrictInfo-r6		OPTIONAL
}

RadioBearerReconfiguration-v890ext-IEs ::= SEQUENCE {
	-- Physical channel IEs
		dl-SecondaryCellInfoFDD-v890ext		DL-SecondaryCellInfoFDD-v890ext		OPTIONAL,
		dl-HSPDSCH-Information				DL-HSPDSCH-Information-r8-ext		OPTIONAL
}

RadioBearerReconfiguration-v8a0ext-IEs ::= SEQUENCE {
	-- Physical channel IEs
		dl-HSPDSCH-Information				DL-HSPDSCH-Information-r8-ext2		OPTIONAL
}

RadioBearerReconfiguration-r9-IEs ::= SEQUENCE {
	-- User equipment IEs
		integrityProtectionModeInfo		IntegrityProtectionModeInfo-r7		OPTIONAL,
		cipheringModeInfo				CipheringModeInfo-r7				OPTIONAL,
		activationTime					ActivationTime						OPTIONAL,
		delayRestrictionFlag			DelayRestrictionFlag				OPTIONAL,
		new-U-RNTI						U-RNTI								OPTIONAL,
		new-C-RNTI						C-RNTI								OPTIONAL,
		-- The IE "new-DSCH-RNTI" should not be included in FDD mode,
		-- and if received the UE behaviour is unspecified
		new-DSCH-RNTI					DSCH-RNTI							OPTIONAL,
		new-H-RNTI						H-RNTI								OPTIONAL,
		newPrimary-E-RNTI				E-RNTI								OPTIONAL,
		newSecondary-E-RNTI				E-RNTI								OPTIONAL,
		rrc-StateIndicator				RRC-StateIndicator,
		ueMobilityStateIndicator		High-MobilityDetected				OPTIONAL,
		utran-DRX-CycleLengthCoeff		UTRAN-DRX-CycleLengthCoefficient-r7	OPTIONAL,
	-- Core network IEs
		cn-InformationInfo				CN-InformationInfo-r6				OPTIONAL,
	-- UTRAN mobility IEs
		ura-Identity					URA-Identity						OPTIONAL,
		supportForChangeOfUE-Capability	BOOLEAN								OPTIONAL,
		responseToChangeOfUE-Capability	ENUMERATED { true }					OPTIONAL,
	-- Specification mode information
		defaultConfigForCellFACH		DefaultConfigForCellFACH			OPTIONAL,
		specificationMode				CHOICE {
			complete						SEQUENCE {
			-- Radio bearer IEs
				rab-InformationReconfigList		RAB-InformationReconfigList-r8		OPTIONAL,
				rab-InformationMBMSPtpList		RAB-InformationMBMSPtpList			OPTIONAL,
				rb-InformationReconfigList		RB-InformationReconfigList-r8		OPTIONAL,
				rb-InformationAffectedList		RB-InformationAffectedList-r8		OPTIONAL,
				rb-PDCPContextRelocationList	RB-PDCPContextRelocationList		OPTIONAL,
				pdcp-ROHC-TargetMode			PDCP-ROHC-TargetMode				OPTIONAL,
			-- Transport channel IEs
				ul-CommonTransChInfo			UL-CommonTransChInfo-r4				OPTIONAL,
				ul-deletedTransChInfoList		UL-DeletedTransChInfoList-r6		OPTIONAL,
				ul-AddReconfTransChInfoList		UL-AddReconfTransChInfoList-r8		OPTIONAL,
				dl-CommonTransChInfo			DL-CommonTransChInfo-r4				OPTIONAL,
				dl-DeletedTransChInfoList		DL-DeletedTransChInfoList-r7		OPTIONAL,
				dl-AddReconfTransChInfoList		DL-AddReconfTransChInfoList-r9		OPTIONAL
			},
			preconfiguration				SEQUENCE {
			-- All IEs that include an FDD/TDD choice are split in two IEs for this message,
			-- one for the FDD only elements and one for the TDD only elements, so that one
			-- FDD/TDD choice in this level is sufficient.
				preConfigMode					CHOICE {
					predefinedConfigIdentity		PredefinedConfigIdentity,
					defaultConfig					SEQUENCE {
						defaultConfigMode				DefaultConfigMode,
						defaultConfigIdentity 			DefaultConfigIdentity-r6
					}
				}
			}
		},
	-- Physical channel IEs
		frequencyInfo					FrequencyInfo						OPTIONAL,
		multi-frequencyInfo				Multi-frequencyInfo-LCR-r7			OPTIONAL,
		dtx-drx-TimingInfo				DTX-DRX-TimingInfo-r7				OPTIONAL,
		dtx-drx-Info					DTX-DRX-Info-r7						OPTIONAL,
		hs-scch-LessInfo				HS-SCCH-LessInfo-r7					OPTIONAL,
		mimoParameters					MIMO-Parameters-r9					OPTIONAL,
		maxAllowedUL-TX-Power			MaxAllowedUL-TX-Power				OPTIONAL,
		ul-DPCH-Info					UL-DPCH-Info-r7						OPTIONAL,
		ul-EDCH-Information				UL-EDCH-Information-r9				OPTIONAL,
		ul-SecondaryCellInfoFDD			UL-SecondaryCellInfoFDD				OPTIONAL,
		dl-HSPDSCH-Information			DL-HSPDSCH-Information-r9			OPTIONAL,
		dl-CommonInformation			DL-CommonInformation-r8				OPTIONAL,
		dl-InformationPerRL-List		DL-InformationPerRL-List-r8			OPTIONAL,
		dl-SecondaryCellInfoFDD			DL-SecondaryCellInfoFDD-r9			OPTIONAL,
		controlChannelDRXInfo-TDD128	ControlChannelDRXInfo-TDD128-r8		OPTIONAL,
		sps-Information-TDD128			SPS-Information-TDD128-r8			OPTIONAL,
	-- MBMS IEs
		mbms-PL-ServiceRestrictInfo		MBMS-PL-ServiceRestrictInfo-r6		OPTIONAL,
	-- Measurement IEs for LCR
		cellDCHMeasOccasionInfo-TDD128	CellDCHMeasOccasionInfo-TDD128-r9	OPTIONAL
}

RadioBearerReconfiguration-v950ext-IEs ::= SEQUENCE {
	-- Physical channel IEs
		secondaryCellMimoParameters		SecondaryCellMIMOparametersFDD-v950ext		OPTIONAL
}

RadioBearerReconfiguration-v9c0ext-IEs ::= SEQUENCE {
	-- For 1.28Mcps TDD only
		dl-AddReconfTransChInfoList		DL-AddReconfTransChInfoList-TDD128-v9c0ext			OPTIONAL
}

RadioBearerReconfiguration-r10-IEs ::= SEQUENCE {
	-- User equipment IEs
		integrityProtectionModeInfo		IntegrityProtectionModeInfo-r7		OPTIONAL,
		cipheringModeInfo				CipheringModeInfo-r7				OPTIONAL,
		activationTime					ActivationTime						OPTIONAL,
		delayRestrictionFlag			DelayRestrictionFlag				OPTIONAL,
		new-U-RNTI						U-RNTI								OPTIONAL,
		new-C-RNTI						C-RNTI								OPTIONAL,
		-- The IE "new-DSCH-RNTI" should not be included in FDD mode,
		-- and if received the UE behaviour is unspecified
		new-DSCH-RNTI					DSCH-RNTI							OPTIONAL,
		new-H-RNTI						H-RNTI								OPTIONAL,
		newPrimary-E-RNTI				E-RNTI								OPTIONAL,
		newSecondary-E-RNTI				E-RNTI								OPTIONAL,
		rrc-StateIndicator				RRC-StateIndicator,
		ueMobilityStateIndicator		High-MobilityDetected				OPTIONAL,
		utran-DRX-CycleLengthCoeff		UTRAN-DRX-CycleLengthCoefficient-r7	OPTIONAL,
	-- Core network IEs
		cn-InformationInfo				CN-InformationInfo-r6				OPTIONAL,
	-- UTRAN mobility IEs
		ura-Identity					URA-Identity						OPTIONAL,
		supportForChangeOfUE-Capability	BOOLEAN								OPTIONAL,
		responseToChangeOfUE-Capability	ENUMERATED { true }					OPTIONAL,
	-- Specification mode information
		defaultConfigForCellFACH		DefaultConfigForCellFACH			OPTIONAL,
		specificationMode				CHOICE {
			complete						SEQUENCE {
			-- Radio bearer IEs
				rab-InformationReconfigList		RAB-InformationReconfigList-r8		OPTIONAL,
				rab-InformationMBMSPtpList		RAB-InformationMBMSPtpList			OPTIONAL,
				rb-InformationReconfigList		RB-InformationReconfigList-r8		OPTIONAL,
				rb-InformationAffectedList		RB-InformationAffectedList-r8		OPTIONAL,
				rb-PDCPContextRelocationList	RB-PDCPContextRelocationList		OPTIONAL,
				pdcp-ROHC-TargetMode			PDCP-ROHC-TargetMode				OPTIONAL,
			-- Transport channel IEs
				ul-CommonTransChInfo			UL-CommonTransChInfo-r4				OPTIONAL,
				ul-deletedTransChInfoList		UL-DeletedTransChInfoList-r6		OPTIONAL,
				ul-AddReconfTransChInfoList		UL-AddReconfTransChInfoList-r8		OPTIONAL,
				dl-CommonTransChInfo			DL-CommonTransChInfo-r4				OPTIONAL,
				dl-DeletedTransChInfoList		DL-DeletedTransChInfoList-r7		OPTIONAL,
				dl-AddReconfTransChInfoList		DL-AddReconfTransChInfoList-r9		OPTIONAL
			},
			preconfiguration				SEQUENCE {
			-- All IEs that include an FDD/TDD choice are split in two IEs for this message,
			-- one for the FDD only elements and one for the TDD only elements, so that one
			-- FDD/TDD choice in this level is sufficient.
				preConfigMode					CHOICE {
					predefinedConfigIdentity		PredefinedConfigIdentity,
					defaultConfig					SEQUENCE {
						defaultConfigMode				DefaultConfigMode,
						defaultConfigIdentity 			DefaultConfigIdentity-r6
					}
				}
			}
		},
	-- Physical channel IEs
		frequencyInfo					FrequencyInfo						OPTIONAL,
		multi-frequencyInfo				Multi-frequencyInfo-LCR-r7			OPTIONAL,
		dtx-drx-TimingInfo				DTX-DRX-TimingInfo-r7				OPTIONAL,
		dtx-drx-Info					DTX-DRX-Info-r7						OPTIONAL,
		hs-scch-LessInfo				HS-SCCH-LessInfo-r7					OPTIONAL,
		mimoParameters					MIMO-Parameters-r9					OPTIONAL,
		maxAllowedUL-TX-Power			MaxAllowedUL-TX-Power				OPTIONAL,
		ul-DPCH-Info					UL-DPCH-Info-r7						OPTIONAL,
		ul-EDCH-Information				UL-EDCH-Information-r9				OPTIONAL,
		ul-SecondaryCellInfoFDD			UL-SecondaryCellInfoFDD				OPTIONAL,
		ul-MulticarrierEDCHInfo-TDD128	UL-MulticarrierEDCHInfo-TDD128		OPTIONAL,
		dl-HSPDSCH-Information			DL-HSPDSCH-Information-r9			OPTIONAL,
		dl-CommonInformation			DL-CommonInformation-r10			OPTIONAL,
		dl-InformationPerRL-List		DL-InformationPerRL-List-r8			OPTIONAL,
		dl-SecondaryCellInfoFDD			DL-SecondaryCellInfoFDD-r10			OPTIONAL,
		additionalDLSecCellInfoListFDD	AdditionalDLSecCellInfoListFDD		OPTIONAL,
		controlChannelDRXInfo-TDD128	ControlChannelDRXInfo-TDD128-r8		OPTIONAL,
		sps-Information-TDD128			SPS-Information-TDD128-r8			OPTIONAL,
		mu-MIMO-Info-TDD128				MU-MIMO-Info-TDD128					OPTIONAL,
	-- MBMS IEs
		mbms-PL-ServiceRestrictInfo		MBMS-PL-ServiceRestrictInfo-r6		OPTIONAL,
	-- Measurement IEs for LCR
		cellDCHMeasOccasionInfo-TDD128	CellDCHMeasOccasionInfo-TDD128-r9	OPTIONAL
}

RadioBearerReconfiguration-vb50ext-IEs ::= SEQUENCE {
		ulOLTDInfoFDD						UL-OLTD-InfoFDD			OPTIONAL
}

RadioBearerReconfiguration-r11-IEs ::= SEQUENCE {
	-- User equipment IEs
		integrityProtectionModeInfo		IntegrityProtectionModeInfo-r7		OPTIONAL,
		cipheringModeInfo				CipheringModeInfo-r7				OPTIONAL,
		activationTime					ActivationTime						OPTIONAL,
		delayRestrictionFlag			DelayRestrictionFlag				OPTIONAL,
		new-U-RNTI						U-RNTI								OPTIONAL,
		new-C-RNTI						C-RNTI								OPTIONAL,
		-- The IE "new-DSCH-RNTI" should not be included in FDD mode,
		-- and if received the UE behaviour is unspecified
		new-DSCH-RNTI					DSCH-RNTI							OPTIONAL,
		new-H-RNTI						H-RNTI								OPTIONAL,
		newPrimary-E-RNTI				E-RNTI								OPTIONAL,
		newSecondary-E-RNTI				E-RNTI								OPTIONAL,
		rrc-StateIndicator				RRC-StateIndicator,
		ueMobilityStateIndicator		High-MobilityDetected				OPTIONAL,
		utran-DRX-CycleLengthCoeff		UTRAN-DRX-CycleLengthCoefficient-r7	OPTIONAL,
	-- Core network IEs
		cn-InformationInfo				CN-InformationInfo-r6				OPTIONAL,
	-- UTRAN mobility IEs
		ura-Identity					URA-Identity						OPTIONAL,
		supportForChangeOfUE-Capability	BOOLEAN								OPTIONAL,
		responseToChangeOfUE-Capability	ENUMERATED { true }					OPTIONAL,
	-- Specification mode information
		defaultConfigForCellFACH		DefaultConfigForCellFACH			OPTIONAL,
		specificationMode				CHOICE {
			complete						SEQUENCE {
			-- Radio bearer IEs
				rab-InformationReconfigList		RAB-InformationReconfigList-r8		OPTIONAL,
				rab-InformationMBMSPtpList		RAB-InformationMBMSPtpList			OPTIONAL,
				rb-InformationReconfigList		RB-InformationReconfigList-r11		OPTIONAL,
				rb-InformationAffectedList		RB-InformationAffectedList-r8		OPTIONAL,
				rb-PDCPContextRelocationList	RB-PDCPContextRelocationList		OPTIONAL,
				pdcp-ROHC-TargetMode			PDCP-ROHC-TargetMode				OPTIONAL,
				umRlc-ReEstablishmentRBList		RB-IdentityList						OPTIONAL,
			-- Transport channel IEs
				ul-CommonTransChInfo			UL-CommonTransChInfo-r4				OPTIONAL,
				ul-deletedTransChInfoList		UL-DeletedTransChInfoList-r6		OPTIONAL,
				ul-AddReconfTransChInfoList		UL-AddReconfTransChInfoList-r8		OPTIONAL,
				dl-CommonTransChInfo			DL-CommonTransChInfo-r4				OPTIONAL,
				dl-DeletedTransChInfoList		DL-DeletedTransChInfoList-r7		OPTIONAL,
				dl-AddReconfTransChInfoList		DL-AddReconfTransChInfoList-r11		OPTIONAL
			},
			preconfiguration				SEQUENCE {
			-- All IEs that include an FDD/TDD choice are split in two IEs for this message,
			-- one for the FDD only elements and one for the TDD only elements, so that one
			-- FDD/TDD choice in this level is sufficient.
				preConfigMode					CHOICE {
					predefinedConfigIdentity		PredefinedConfigIdentity,
					defaultConfig					SEQUENCE {
						defaultConfigMode				DefaultConfigMode,
						defaultConfigIdentity 			DefaultConfigIdentity-r6
					}
				}
			}
		},
	-- Physical channel IEs
		frequencyInfo					FrequencyInfo						OPTIONAL,
		multi-frequencyInfo				Multi-frequencyInfo-LCR-r7			OPTIONAL,
		dtx-drx-TimingInfo				DTX-DRX-TimingInfo-r7				OPTIONAL,
		dtx-drx-Info					DTX-DRX-Info-r7						OPTIONAL,
		hs-scch-LessInfo				HS-SCCH-LessInfo-r7					OPTIONAL,
		mimoParameters					MIMO-Parameters-r9					OPTIONAL,
		mimo4x4Parameters				MIMO4x4-Parameters					OPTIONAL,
		maxAllowedUL-TX-Power			MaxAllowedUL-TX-Power				OPTIONAL,
		ul-DPCH-Info					UL-DPCH-Info-r11						OPTIONAL,
		ul-EDCH-Information				UL-EDCH-Information-r11				OPTIONAL,
		ul-SecondaryCellInfoFDD			UL-SecondaryCellInfoFDD				OPTIONAL,
		ul-MulticarrierEDCHInfo-TDD128	UL-MulticarrierEDCHInfo-TDD128		OPTIONAL,
		ul-CLTD-InfoFDD					UL-CLTD-InfoFDD						OPTIONAL,
		ul-OLTD-InfoFDD					UL-OLTD-InfoFDD						OPTIONAL,
		dl-HSPDSCH-Information			DL-HSPDSCH-Information-r11			OPTIONAL,
		dl-CommonInformation			DL-CommonInformation-r11			OPTIONAL,
		dl-InformationPerRL-List		DL-InformationPerRL-List-r11			OPTIONAL,
		dl-SecondaryCellInfoFDD			DL-SecondaryCellInfoFDD-r11			OPTIONAL,
		additionalDLSecCellInfoListFDD	AdditionalDLSecCellInfoListFDD-r11	OPTIONAL,
		additionalDLSecCellInfoListFDD2	AdditionalDLSecCellInfoListFDD2		OPTIONAL,
		commonERGCHInfoFDD				CommonERGCHInfoFDD					OPTIONAL,
		controlChannelDRXInfo-TDD128	ControlChannelDRXInfo-TDD128-r8		OPTIONAL,
		sps-Information-TDD128			SPS-Information-TDD128-r8			OPTIONAL,
		mu-MIMO-Info-TDD128				MU-MIMO-Info-TDD128					OPTIONAL,
	-- MBMS IEs
		mbms-PL-ServiceRestrictInfo		MBMS-PL-ServiceRestrictInfo-r6		OPTIONAL,
	-- Measurement IEs for LCR
		cellDCHMeasOccasionInfo-TDD128	CellDCHMeasOccasionInfo-TDD128-r9	OPTIONAL
}

-- ***************************************************
--
-- RADIO BEARER RECONFIGURATION COMPLETE
--
-- ***************************************************

RadioBearerReconfigurationComplete ::= SEQUENCE {
	-- User equipment IEs
		rrc-TransactionIdentifier		RRC-TransactionIdentifier,
		ul-IntegProtActivationInfo		IntegrityProtActivationInfo			OPTIONAL,
		-- TABULAR: UL-TimingAdvance is applicable for TDD mode only.
		ul-TimingAdvance				UL-TimingAdvance					OPTIONAL,
	-- Radio bearer IEs
		count-C-ActivationTime			ActivationTime						OPTIONAL,
		-- dummy is not used in this version of the specification and
		-- it should be ignored by the receiver.
		dummy							RB-ActivationTimeInfoList			OPTIONAL,
		ul-CounterSynchronisationInfo	UL-CounterSynchronisationInfo		OPTIONAL,
		laterNonCriticalExtensions		SEQUENCE {
			-- Container for additional R99 extensions
			radioBearerReconfigurationComplete-r3-add-ext		BIT STRING		OPTIONAL,
			v770NonCriticalExtensions		SEQUENCE {
				radioBearerReconfigurationComplete-v770ext
												RadioBearerReconfigurationComplete-v770ext-IEs,
				nonCriticalExtensions			SEQUENCE {}	OPTIONAL
			}	OPTIONAL
		}	OPTIONAL
}

RadioBearerReconfigurationComplete-v770ext-IEs ::= SEQUENCE {
		-- TABULAR: EXT-UL-TimingAdvance is applicable for TDD mode only.
		ext-UL-TimingAdvance					EXT-UL-TimingAdvance	OPTIONAL,
		deferredMeasurementControlReading		ENUMERATED { true }		OPTIONAL
}

-- ***************************************************
--
-- RADIO BEARER RECONFIGURATION FAILURE
--
-- ***************************************************

RadioBearerReconfigurationFailure ::= SEQUENCE {
	-- User equipment IEs
		rrc-TransactionIdentifier		RRC-TransactionIdentifier,
		failureCause					FailureCauseWithProtErr,
	-- Radio bearer IEs
		potentiallySuccesfulBearerList	RB-IdentityList						OPTIONAL,
		laterNonCriticalExtensions		SEQUENCE {
			-- Container for additional R99 extensions
			radioBearerReconfigurationFailure-r3-add-ext		BIT STRING		OPTIONAL,
			nonCriticalExtensions			SEQUENCE {}	OPTIONAL
		}	OPTIONAL
}

-- ***************************************************
--
-- RADIO BEARER RELEASE
--
-- ***************************************************

RadioBearerRelease ::= CHOICE {
	r3								SEQUENCE {
		radioBearerRelease-r3			RadioBearerRelease-r3-IEs,
		v3a0NonCriticalExtensions		SEQUENCE {
			radioBearerRelease-v3a0ext		RadioBearerRelease-v3a0ext,
		laterNonCriticalExtensions		SEQUENCE {
			-- Container for additional R99 extensions
			radioBearerRelease-r3-add-ext		BIT STRING		OPTIONAL,
				v4b0NonCriticalExtensions		SEQUENCE {
					radioBearerRelease-v4b0ext		RadioBearerRelease-v4b0ext-IEs,
					v590NonCriticalExtensions		SEQUENCE {
						radioBearerRelease-v590ext		RadioBearerRelease-v590ext-IEs,
						v690NonCriticalExtensions		SEQUENCE {
							radioBearerRelease-v690ext		RadioBearerRelease-v690ext-IEs,
							v770NonCriticalExtensions		SEQUENCE {
								radioBearerRelease-v770ext		RadioBearerRelease-v770ext-IEs,
								nonCriticalExtensions			SEQUENCE {} OPTIONAL
							}	OPTIONAL
						}	OPTIONAL
					}	OPTIONAL
				}	OPTIONAL
			}	OPTIONAL
		}	OPTIONAL
	},
	later-than-r3					SEQUENCE {
		rrc-TransactionIdentifier		RRC-TransactionIdentifier,
		criticalExtensions				CHOICE {
			r4								SEQUENCE {
				radioBearerRelease-r4			RadioBearerRelease-r4-IEs,
				v4d0NonCriticalExtensions			SEQUENCE {
					-- Container for adding non critical extensions after freezing REL-5
					radioBearerRelease-r4-add-ext		BIT STRING		OPTIONAL,
					v590NonCriticalExtensions		SEQUENCE {
						radioBearerRelease-v590ext		RadioBearerRelease-v590ext-IEs,
						v690NonCriticalExtensions		SEQUENCE {
							radioBearerRelease-v690ext		RadioBearerRelease-v690ext-IEs,
							v770NonCriticalExtensions		SEQUENCE {
								radioBearerRelease-v770ext		RadioBearerRelease-v770ext-IEs,
								nonCriticalExtensions			SEQUENCE {}		OPTIONAL
							}	OPTIONAL
						}	OPTIONAL
					}	OPTIONAL
				}	OPTIONAL
			},
			criticalExtensions				CHOICE {
				r5								SEQUENCE {
					radioBearerRelease-r5			RadioBearerRelease-r5-IEs,
					-- Container for adding non critical extensions after freezing REL-6
					radioBearerRelease-r5-add-ext	BIT STRING		OPTIONAL,
					v690NonCriticalExtensions		SEQUENCE {
						radioBearerRelease-v690ext		RadioBearerRelease-v690ext-IEs,
						v770NonCriticalExtensions		SEQUENCE {
							radioBearerRelease-v770ext		RadioBearerRelease-v770ext-IEs,
							nonCriticalExtensions			SEQUENCE {}		OPTIONAL
						}	OPTIONAL
					}	OPTIONAL
				},
				criticalExtensions				CHOICE {
					r6								SEQUENCE {
						radioBearerRelease-r6			RadioBearerRelease-r6-IEs,
						-- Container for adding non critical extensions after freezing REL-7
						radioBearerRelease-r6-add-ext	BIT STRING		OPTIONAL,
						v6b0NonCriticalExtensions		SEQUENCE {
							radioBearerRelease-v6b0ext		RadioBearerRelease-v6b0ext-IEs,
							v770NonCriticalExtensions		SEQUENCE {
								radioBearerRelease-v770ext		RadioBearerRelease-v770ext-IEs,
								nonCriticalExtensions			SEQUENCE {}		OPTIONAL
							}	OPTIONAL
						}	OPTIONAL
					},
					criticalExtensions				CHOICE {
						r7								SEQUENCE {
							radioBearerRelease-r7			RadioBearerRelease-r7-IEs,
							-- Container for adding non critical extensions after freezing REL-8
							radioBearerRelease-r7-add-ext	BIT STRING		OPTIONAL,
							v780NonCriticalExtensions		SEQUENCE {
								radioBearerRelease-v780ext		RadioBearerRelease-v780ext-IEs,
								v7d0NonCriticalExtensions		SEQUENCE {
									radioBearerRelease-v7d0ext		RadioBearerRelease-v7d0ext-IEs,
									v7f0NonCriticalExtensions		SEQUENCE {
										radioBearerRelease-v7f0ext	RadioBearerRelease-v7f0ext-IEs,
										v7g0NonCriticalExtensions		SEQUENCE {
											radioBearerRelease-v7g0ext	
																	RadioBearerRelease-v7g0ext-IEs,
											nonCriticalExtensions	SEQUENCE {}		OPTIONAL
										}	OPTIONAL
									}	OPTIONAL
								}	OPTIONAL
							}	OPTIONAL
						},
						criticalExtensions				CHOICE {
							r8								SEQUENCE {
								radioBearerRelease-r8			RadioBearerRelease-r8-IEs,
								-- Container for adding non critical extensions after freezing REL-9
								radioBearerRelease-r8-add-ext	BIT STRING		OPTIONAL,
								v7d0NonCriticalExtensions		SEQUENCE {
									radioBearerRelease-v7d0ext		RadioBearerRelease-v7d0ext-IEs,
									v7f0NonCriticalExtensions		SEQUENCE {
										radioBearerRelease-v7f0ext	RadioBearerRelease-v7f0ext-IEs,
										v890NonCriticalExtensions		SEQUENCE {
											radioBearerRelease-v890ext
																	RadioBearerRelease-v890ext-IEs,
											v7g0NonCriticalExtensions		SEQUENCE {
												radioBearerRelease-v7g0ext	
																	RadioBearerRelease-v7g0ext-IEs,
												v8a0NonCriticalExtensions		SEQUENCE {
													radioBearerRelease-v8a0ext
																	RadioBearerRelease-v8a0ext-IEs,
													nonCriticalExtensions	
																	SEQUENCE {}		OPTIONAL
												}	OPTIONAL
											}	OPTIONAL
										}	OPTIONAL
									}	OPTIONAL
								}	OPTIONAL
							},
							criticalExtensions				CHOICE {
								r9								SEQUENCE {
									radioBearerRelease-r9			RadioBearerRelease-r9-IEs,
									-- Container for adding non critical extensions after 
									-- freezing REL-10
									radioBearerRelease-r9-add-ext	BIT STRING		OPTIONAL,
									v950NonCriticalExtensions		SEQUENCE {
										radioBearerRelease-v950ext	RadioBearerRelease-v950ext-IEs,
										v970NonCriticalExtensions		SEQUENCE {
											radioBearerRelease-v970ext	RadioBearerRelease-v970ext-IEs,
											v9c0NonCriticalExtensions		SEQUENCE {
												radioBearerRelease-v9c0ext	RadioBearerRelease-v9c0ext-IEs,
												nonCriticalExtensions		SEQUENCE {}		OPTIONAL
											}	OPTIONAL
										}	OPTIONAL
									}	OPTIONAL
								},
								criticalExtensions				CHOICE {
									r10								SEQUENCE {
										radioBearerRelease-r10			RadioBearerRelease-r10-IEs,
										-- Container for adding non critical extensions after 
										-- freezing REL-11
										radioBearerRelease-r10-add-ext	BIT STRING		OPTIONAL,
										v9c0NonCriticalExtensions		SEQUENCE {
												radioBearerRelease-v9c0ext	RadioBearerRelease-v9c0ext-IEs,
											vb50NonCriticalExtensions		SEQUENCE {
												radioBearerRelease-vb50ext
																	RadioBearerRelease-vb50ext-IEs,
												nonCriticalExtensions		SEQUENCE {}		OPTIONAL
											}	OPTIONAL
										}	OPTIONAL
									},
									criticalExtensions				CHOICE {
										r11								SEQUENCE {
											radioBearerRelease-r11			
																		RadioBearerRelease-r11-IEs,
											-- Container for adding non critical extensions after 
											-- freezing REL-12
											radioBearerRelease-r11-add-ext	
																		BIT STRING		OPTIONAL,
											nonCriticalExtensions		SEQUENCE {}		OPTIONAL
										},
										criticalExtensions				SEQUENCE {}
									}
								}
							}
						}
					}
				}
			}
		}
	}
}

RadioBearerRelease-r3-IEs ::= SEQUENCE {
	-- User equipment IEs
		rrc-TransactionIdentifier		RRC-TransactionIdentifier,
		integrityProtectionModeInfo		IntegrityProtectionModeInfo			OPTIONAL,
		cipheringModeInfo				CipheringModeInfo					OPTIONAL,
		activationTime					ActivationTime						OPTIONAL,
		new-U-RNTI						U-RNTI								OPTIONAL,
		new-C-RNTI						C-RNTI								OPTIONAL,
		rrc-StateIndicator				RRC-StateIndicator,
		utran-DRX-CycleLengthCoeff		UTRAN-DRX-CycleLengthCoefficient	OPTIONAL,
	-- Core network IEs
		cn-InformationInfo				CN-InformationInfo					OPTIONAL,
		signallingConnectionRelIndication	CN-DomainIdentity		     	OPTIONAL,
	-- UTRAN mobility IEs
		ura-Identity					URA-Identity						OPTIONAL,
	-- Radio bearer IEs
		rab-InformationReconfigList		RAB-InformationReconfigList			OPTIONAL,
		rb-InformationReleaseList		RB-InformationReleaseList,
		rb-InformationAffectedList		RB-InformationAffectedList			OPTIONAL,
		dl-CounterSynchronisationInfo	DL-CounterSynchronisationInfo		OPTIONAL,
	-- Transport channel IEs
		ul-CommonTransChInfo			UL-CommonTransChInfo				OPTIONAL,
		ul-deletedTransChInfoList		UL-DeletedTransChInfoList			OPTIONAL,
		ul-AddReconfTransChInfoList		UL-AddReconfTransChInfoList			OPTIONAL,
		-- 'dummy', 'dummy1' and 'dummy2' are not used in this version of the specification,
		-- they should not be sent and if received they should be ignored.
		dummy							CHOICE {
			fdd								SEQUENCE {
				dummy1							CPCH-SetID					OPTIONAL,
				dummy2							DRAC-StaticInformationList	OPTIONAL
			},
			tdd								NULL
		}																	OPTIONAL,
		dl-CommonTransChInfo			DL-CommonTransChInfo				OPTIONAL,
		dl-DeletedTransChInfoList		DL-DeletedTransChInfoList			OPTIONAL,
		dl-AddReconfTransChInfoList		DL-AddReconfTransChInfo2List		OPTIONAL,
	-- Physical channel IEs
		frequencyInfo					FrequencyInfo						OPTIONAL,
		maxAllowedUL-TX-Power			MaxAllowedUL-TX-Power				OPTIONAL,
		ul-ChannelRequirement			UL-ChannelRequirement				OPTIONAL,
		modeSpecificPhysChInfo			CHOICE {
			fdd								SEQUENCE {
				-- dummy is not used in this version of specification, it should
				-- not be sent and if received it should be ignored.
				dummy							DL-PDSCH-Information		OPTIONAL
			},
			tdd							NULL
		},
		dl-CommonInformation			DL-CommonInformation				OPTIONAL,
		dl-InformationPerRL-List		DL-InformationPerRL-List			OPTIONAL
}

RadioBearerRelease-v3a0ext ::= SEQUENCE {
	-- The IE "new-DSCH-RNTI" should not be included in FDD mode, and if received the UE behaviour
	-- is unspecified
	new-DSCH-RNTI					DSCH-RNTI							OPTIONAL
}

RadioBearerRelease-v4b0ext-IEs ::= SEQUENCE {
	-- Physical channel IEs
		-- dummy is not used in this version of the specification, it should
		-- not be sent and if received it should be ignored.
		dummy								SSDT-UL								OPTIONAL,
		-- The order of the RLs in IE cell-id-PerRL-List is the same as
		--  in IE DL-InformationPerRL-List included in this message
		cell-id-PerRL-List					CellIdentity-PerRL-List				OPTIONAL
}

RadioBearerRelease-v590ext-IEs ::= SEQUENCE {
	-- Physical channel IEs
		dl-TPC-PowerOffsetPerRL-List	DL-TPC-PowerOffsetPerRL-List		OPTIONAL
}

RadioBearerRelease-r4-IEs ::= SEQUENCE {
	-- User equipment IEs
		integrityProtectionModeInfo		IntegrityProtectionModeInfo			OPTIONAL,
		cipheringModeInfo				CipheringModeInfo					OPTIONAL,
		activationTime					ActivationTime						OPTIONAL,
		new-U-RNTI						U-RNTI								OPTIONAL,
		new-C-RNTI						C-RNTI								OPTIONAL,
		-- The IE "new-DSCH-RNTI" should not be included in FDD mode, and if received
		-- the UE behaviour is unspecified
		new-DSCH-RNTI					DSCH-RNTI							OPTIONAL,
		rrc-StateIndicator				RRC-StateIndicator,
		utran-DRX-CycleLengthCoeff		UTRAN-DRX-CycleLengthCoefficient	OPTIONAL,
	-- Core network IEs
		cn-InformationInfo				CN-InformationInfo					OPTIONAL,
		signallingConnectionRelIndication	CN-DomainIdentity				OPTIONAL,
	-- UTRAN mobility IEs
		ura-Identity					URA-Identity						OPTIONAL,
	-- Radio bearer IEs
		rab-InformationReconfigList		RAB-InformationReconfigList			OPTIONAL,
		rb-InformationReleaseList		RB-InformationReleaseList,
		rb-InformationAffectedList		RB-InformationAffectedList			OPTIONAL,
		dl-CounterSynchronisationInfo	DL-CounterSynchronisationInfo		OPTIONAL,
	-- Transport channel IEs
		ul-CommonTransChInfo			UL-CommonTransChInfo-r4				OPTIONAL,
		ul-deletedTransChInfoList		UL-DeletedTransChInfoList			OPTIONAL,
		ul-AddReconfTransChInfoList		UL-AddReconfTransChInfoList			OPTIONAL,
		-- 'dummy', 'dummy1' and 'dummy2' are not used in this version of the specification,
		-- they should not be sent and if received they should be ignored.
		dummy							CHOICE {
			fdd								SEQUENCE {
				dummy1							CPCH-SetID					OPTIONAL,
				dummy2							DRAC-StaticInformationList	OPTIONAL
			},
			tdd								NULL
		}																	OPTIONAL,
		dl-CommonTransChInfo			DL-CommonTransChInfo-r4				OPTIONAL,
		dl-DeletedTransChInfoList		DL-DeletedTransChInfoList			OPTIONAL,
		dl-AddReconfTransChInfoList		DL-AddReconfTransChInfoList-r4		OPTIONAL,
	-- Physical channel IEs
		frequencyInfo					FrequencyInfo						OPTIONAL,
		maxAllowedUL-TX-Power			MaxAllowedUL-TX-Power				OPTIONAL,
		ul-ChannelRequirement			UL-ChannelRequirement-r4			OPTIONAL,
		modeSpecificPhysChInfo			CHOICE {
			fdd								SEQUENCE {
				-- dummy is not used in this version of specification, it should
				-- not be sent and if received it should be ignored.
				dummy							DL-PDSCH-Information		OPTIONAL
			},
			tdd							NULL
		},
		dl-CommonInformation			DL-CommonInformation-r4				OPTIONAL,
		dl-InformationPerRL-List		DL-InformationPerRL-List-r4			OPTIONAL
}

RadioBearerRelease-r5-IEs ::= SEQUENCE {
	-- User equipment IEs
		integrityProtectionModeInfo		IntegrityProtectionModeInfo			OPTIONAL,
		cipheringModeInfo				CipheringModeInfo					OPTIONAL,
		activationTime					ActivationTime						OPTIONAL,
		new-U-RNTI						U-RNTI								OPTIONAL,
		new-C-RNTI						C-RNTI								OPTIONAL,
		-- The IE "new-DSCH-RNTI should not be included in FDD mode,
		-- and if received the UE behaviour is unspecified
		new-DSCH-RNTI					DSCH-RNTI							OPTIONAL,
		new-H-RNTI						H-RNTI								OPTIONAL,
		rrc-StateIndicator				RRC-StateIndicator,
		utran-DRX-CycleLengthCoeff		UTRAN-DRX-CycleLengthCoefficient	OPTIONAL,
	-- Core network IEs
		cn-InformationInfo				CN-InformationInfo					OPTIONAL,
		signallingConnectionRelIndication	CN-DomainIdentity		     	OPTIONAL,
	-- UTRAN mobility IEs
		ura-Identity					URA-Identity						OPTIONAL,
	-- Radio bearer IEs
		rab-InformationReconfigList		RAB-InformationReconfigList			OPTIONAL,
		rb-InformationReleaseList		RB-InformationReleaseList,
		rb-InformationAffectedList		RB-InformationAffectedList-r5		OPTIONAL,
		dl-CounterSynchronisationInfo	DL-CounterSynchronisationInfo-r5	OPTIONAL,
	-- Transport channel IEs
		ul-CommonTransChInfo			UL-CommonTransChInfo-r4				OPTIONAL,
		ul-deletedTransChInfoList		UL-DeletedTransChInfoList			OPTIONAL,
		ul-AddReconfTransChInfoList		UL-AddReconfTransChInfoList			OPTIONAL,
		-- 'dummy', 'dummy1' and 'dummy2' are not used in this version of the specification,
		-- they should not be sent and if received they should be ignored.
		dummy							CHOICE {
			fdd								SEQUENCE {
				dummy1							CPCH-SetID					OPTIONAL,
				dummy2							DRAC-StaticInformationList	OPTIONAL
			},
			tdd								NULL
		}																	OPTIONAL,
		dl-CommonTransChInfo			DL-CommonTransChInfo-r4				OPTIONAL,
		dl-DeletedTransChInfoList		DL-DeletedTransChInfoList-r5		OPTIONAL,
		dl-AddReconfTransChInfoList		DL-AddReconfTransChInfoList-r5		OPTIONAL,
	-- Physical channel IEs
		frequencyInfo					FrequencyInfo						OPTIONAL,
		maxAllowedUL-TX-Power			MaxAllowedUL-TX-Power				OPTIONAL,
		ul-ChannelRequirement			UL-ChannelRequirement-r5			OPTIONAL,
		modeSpecificPhysChInfo			CHOICE {
			fdd								SEQUENCE {
				-- dummy is not used in this version of specification, it should
				-- not be sent and if received it should be ignored.
				dummy							DL-PDSCH-Information		OPTIONAL
			},
			tdd							NULL
		},
		dl-HSPDSCH-Information			DL-HSPDSCH-Information				OPTIONAL,
		dl-CommonInformation			DL-CommonInformation-r5				OPTIONAL,
		dl-InformationPerRL-List		DL-InformationPerRL-List-r5			OPTIONAL
}

RadioBearerRelease-v690ext-IEs ::= SEQUENCE {
	-- Core network IEs
		primary-plmn-Identity			PLMN-Identity						OPTIONAL,
	-- Physical channel IEs
		-- The IE harq-Preamble-Mode should not be used in the r3 and r4 versions of the message
		-- If included in the r3 or r4 version of the message, the UE should ignore the IE
		harq-Preamble-Mode				HARQ-Preamble-Mode					OPTIONAL,
		beaconPLEst						BEACON-PL-Est						OPTIONAL,
		postVerificationPeriod			ENUMERATED { true }					OPTIONAL,
		dhs-sync						DHS-Sync							OPTIONAL,
		timingMaintainedSynchInd		TimingMaintainedSynchInd			OPTIONAL,
	-- MBMS IEs
		mbms-PL-ServiceRestrictInfo		MBMS-PL-ServiceRestrictInfo-r6		OPTIONAL,
		mbms-RB-ListReleasedToChangeTransferMode
										RB-InformationReleaseList			OPTIONAL
}

RadioBearerRelease-r6-IEs ::= SEQUENCE {
	-- User equipment IEs
		integrityProtectionModeInfo		IntegrityProtectionModeInfo			OPTIONAL,
		cipheringModeInfo				CipheringModeInfo					OPTIONAL,
		activationTime					ActivationTime						OPTIONAL,
		new-U-RNTI						U-RNTI								OPTIONAL,
		new-C-RNTI						C-RNTI								OPTIONAL,
		-- The IE "new-DSCH-RNTI" should not be included in FDD mode,
		-- and if received the UE behaviour is unspecified
		new-DSCH-RNTI					DSCH-RNTI							OPTIONAL,
		new-H-RNTI						H-RNTI								OPTIONAL,
		newPrimary-E-RNTI				E-RNTI								OPTIONAL,
		newSecondary-E-RNTI				E-RNTI								OPTIONAL,
		rrc-StateIndicator				RRC-StateIndicator,
		utran-DRX-CycleLengthCoeff		UTRAN-DRX-CycleLengthCoefficient	OPTIONAL,
	-- Core network IEs
		cn-InformationInfo				CN-InformationInfo-r6				OPTIONAL,
		signallingConnectionRelIndication	CN-DomainIdentity				OPTIONAL,
	-- UTRAN mobility IEs
		ura-Identity					URA-Identity						OPTIONAL,
	-- Radio bearer IEs
		rab-InformationReconfigList		RAB-InformationReconfigList			OPTIONAL,
		rb-InformationReleaseList		RB-InformationReleaseList,
		rb-InformationReconfigList		RB-InformationReconfigList-r6		OPTIONAL,
		rb-InformationAffectedList		RB-InformationAffectedList-r6		OPTIONAL,
		dl-CounterSynchronisationInfo	DL-CounterSynchronisationInfo-r5	OPTIONAL,
	-- Transport channel IEs
		ul-CommonTransChInfo			UL-CommonTransChInfo-r4				OPTIONAL,
		ul-deletedTransChInfoList		UL-DeletedTransChInfoList-r6		OPTIONAL,
		ul-AddReconfTransChInfoList		UL-AddReconfTransChInfoList-r6		OPTIONAL,
		dl-CommonTransChInfo			DL-CommonTransChInfo-r4				OPTIONAL,
		dl-DeletedTransChInfoList		DL-DeletedTransChInfoList-r5		OPTIONAL,
		dl-AddReconfTransChInfoList		DL-AddReconfTransChInfoList-r5		OPTIONAL,
	-- Physical channel IEs
		frequencyInfo					FrequencyInfo						OPTIONAL,
		maxAllowedUL-TX-Power			MaxAllowedUL-TX-Power				OPTIONAL,
		ul-DPCH-Info					UL-DPCH-Info-r6						OPTIONAL,
		ul-EDCH-Information				UL-EDCH-Information-r6				OPTIONAL,
		dl-HSPDSCH-Information			DL-HSPDSCH-Information-r6			OPTIONAL,
		dl-CommonInformation			DL-CommonInformation-r6				OPTIONAL,
		dl-InformationPerRL-List		DL-InformationPerRL-List-r6			OPTIONAL,
	-- MBMS IEs
		mbms-PL-ServiceRestrictInfo		MBMS-PL-ServiceRestrictInfo-r6		OPTIONAL,
		mbms-RB-ListReleasedToChangeTransferMode
										RB-InformationReleaseList			OPTIONAL
}

RadioBearerRelease-v6b0ext-IEs ::= SEQUENCE {
	-- Physical channel IEs
		dl-InformationPerRL-List-v6b0ext	DL-InformationPerRL-List-v6b0ext	OPTIONAL
}

RadioBearerRelease-r7-IEs ::= SEQUENCE {
	-- User equipment IEs
		integrityProtectionModeInfo		IntegrityProtectionModeInfo-r7		OPTIONAL,
		cipheringModeInfo				CipheringModeInfo-r7				OPTIONAL,
		activationTime					ActivationTime						OPTIONAL,
		new-U-RNTI						U-RNTI								OPTIONAL,
		new-C-RNTI						C-RNTI								OPTIONAL,
		-- The IE "new-DSCH-RNTI" should not be included in FDD mode,
		-- and if received the UE behaviour is unspecified
		new-DSCH-RNTI					DSCH-RNTI							OPTIONAL,
		new-H-RNTI						H-RNTI								OPTIONAL,
		newPrimary-E-RNTI				E-RNTI								OPTIONAL,
		newSecondary-E-RNTI				E-RNTI								OPTIONAL,
		rrc-StateIndicator				RRC-StateIndicator,
		ueMobilityStateIndicator		High-MobilityDetected				OPTIONAL,
		utran-DRX-CycleLengthCoeff		UTRAN-DRX-CycleLengthCoefficient-r7	OPTIONAL,
	-- Core network IEs
		cn-InformationInfo				CN-InformationInfo-r6				OPTIONAL,
		signallingConnectionRelIndication	CN-DomainIdentity				OPTIONAL,
	-- UTRAN mobility IEs
		ura-Identity					URA-Identity						OPTIONAL,
		supportForChangeOfUE-Capability	BOOLEAN								OPTIONAL,
	-- Radio bearer IEs
		rab-InformationReconfigList		RAB-InformationReconfigList			OPTIONAL,
		rb-InformationReleaseList		RB-InformationReleaseList,
		rb-InformationReconfigList		RB-InformationReconfigList-r7		OPTIONAL,
		rb-InformationAffectedList		RB-InformationAffectedList-r7		OPTIONAL,
		dl-CounterSynchronisationInfo	DL-CounterSynchronisationInfo-r5	OPTIONAL,
	-- Transport channel IEs
		ul-CommonTransChInfo			UL-CommonTransChInfo-r4				OPTIONAL,
		ul-deletedTransChInfoList		UL-DeletedTransChInfoList-r6		OPTIONAL,
		ul-AddReconfTransChInfoList		UL-AddReconfTransChInfoList-r7		OPTIONAL,
		dl-CommonTransChInfo			DL-CommonTransChInfo-r4				OPTIONAL,
		dl-DeletedTransChInfoList		DL-DeletedTransChInfoList-r7		OPTIONAL,
		dl-AddReconfTransChInfoList		DL-AddReconfTransChInfoList-r7		OPTIONAL,
	-- Physical channel IEs
		frequencyInfo					FrequencyInfo						OPTIONAL,
		multi-frequencyInfo				Multi-frequencyInfo-LCR-r7			OPTIONAL,
		dtx-drx-TimingInfo				DTX-DRX-TimingInfo-r7				OPTIONAL,
		dtx-drx-Info					DTX-DRX-Info-r7						OPTIONAL,
		hs-scch-LessInfo				HS-SCCH-LessInfo-r7					OPTIONAL,
		mimoParameters					MIMO-Parameters-r7					OPTIONAL,
		maxAllowedUL-TX-Power			MaxAllowedUL-TX-Power				OPTIONAL,
		ul-DPCH-Info					UL-DPCH-Info-r7						OPTIONAL,
		ul-EDCH-Information				UL-EDCH-Information-r7				OPTIONAL,
		dl-HSPDSCH-Information			DL-HSPDSCH-Information-r7			OPTIONAL,
		dl-CommonInformation			DL-CommonInformation-r7				OPTIONAL,
		dl-InformationPerRL-List		DL-InformationPerRL-List-r7			OPTIONAL,
	-- MBMS IEs
		mbms-PL-ServiceRestrictInfo		MBMS-PL-ServiceRestrictInfo-r6		OPTIONAL,
		mbms-RB-ListReleasedToChangeTransferMode
										RB-InformationReleaseList			OPTIONAL
}

RadioBearerRelease-v770ext-IEs ::= SEQUENCE {
	-- User equipment IEs
		ueMobilityStateIndicator		High-MobilityDetected				OPTIONAL
}

RadioBearerRelease-v780ext-IEs ::= SEQUENCE {
	-- Physical channel IEs
		hs-DSCH-TBSizeTable				HS-DSCH-TBSizeTable					OPTIONAL
}

RadioBearerRelease-v7d0ext-IEs ::= SEQUENCE {
	-- Physical channel IEs
		ul-EDCH-Information				UL-EDCH-Information-ext				OPTIONAL
}

RadioBearerRelease-v7f0ext-IEs ::= SEQUENCE {
	-- Physical channel IEs
	mimoParameters						MIMO-Parameters-v7f0ext				OPTIONAL
}

RadioBearerRelease-v7g0ext-IEs ::= SEQUENCE {
	-- Physical channel IEs
	mimoParameters						MIMO-Parameters-v7g0ext				OPTIONAL
}

RadioBearerRelease-r8-IEs ::= SEQUENCE {
	-- User equipment IEs
		integrityProtectionModeInfo		IntegrityProtectionModeInfo-r7		OPTIONAL,
		cipheringModeInfo				CipheringModeInfo-r7				OPTIONAL,
		activationTime					ActivationTime						OPTIONAL,
		new-U-RNTI						U-RNTI								OPTIONAL,
		new-C-RNTI						C-RNTI								OPTIONAL,
		-- The IE "new-DSCH-RNTI" should not be included in FDD mode,
		-- and if received the UE behaviour is unspecified
		new-DSCH-RNTI					DSCH-RNTI							OPTIONAL,
		new-H-RNTI						H-RNTI								OPTIONAL,
		newPrimary-E-RNTI				E-RNTI								OPTIONAL,
		newSecondary-E-RNTI				E-RNTI								OPTIONAL,
		rrc-StateIndicator				RRC-StateIndicator,
		ueMobilityStateIndicator		High-MobilityDetected				OPTIONAL,
		utran-DRX-CycleLengthCoeff		UTRAN-DRX-CycleLengthCoefficient-r7	OPTIONAL,
	-- Core network IEs
		cn-InformationInfo				CN-InformationInfo-r6				OPTIONAL,
		signallingConnectionRelIndication	CN-DomainIdentity				OPTIONAL,
	-- UTRAN mobility IEs
		ura-Identity					URA-Identity						OPTIONAL,
		supportForChangeOfUE-Capability	BOOLEAN								OPTIONAL,
	-- Radio bearer IEs
		rab-InformationReconfigList		RAB-InformationReconfigList-r8		OPTIONAL,
		rb-InformationReleaseList		RB-InformationReleaseList,
		rb-InformationReconfigList		RB-InformationReconfigList-r8		OPTIONAL,
		rb-InformationAffectedList		RB-InformationAffectedList-r8		OPTIONAL,
		dl-CounterSynchronisationInfo	DL-CounterSynchronisationInfo-r5	OPTIONAL,
	-- Transport channel IEs
		ul-CommonTransChInfo			UL-CommonTransChInfo-r4				OPTIONAL,
		ul-deletedTransChInfoList		UL-DeletedTransChInfoList-r6		OPTIONAL,
		ul-AddReconfTransChInfoList		UL-AddReconfTransChInfoList-r8		OPTIONAL,
		dl-CommonTransChInfo			DL-CommonTransChInfo-r4				OPTIONAL,
		dl-DeletedTransChInfoList		DL-DeletedTransChInfoList-r7		OPTIONAL,
		dl-AddReconfTransChInfoList		DL-AddReconfTransChInfoList-r7		OPTIONAL,
	-- Physical channel IEs
		frequencyInfo					FrequencyInfo						OPTIONAL,
		multi-frequencyInfo				Multi-frequencyInfo-LCR-r7			OPTIONAL,
		dtx-drx-TimingInfo				DTX-DRX-TimingInfo-r7				OPTIONAL,
		dtx-drx-Info					DTX-DRX-Info-r7						OPTIONAL,
		hs-scch-LessInfo				HS-SCCH-LessInfo-r7					OPTIONAL,
		mimoParameters					MIMO-Parameters-r8					OPTIONAL,
		maxAllowedUL-TX-Power			MaxAllowedUL-TX-Power				OPTIONAL,
		ul-DPCH-Info					UL-DPCH-Info-r7						OPTIONAL,
		ul-EDCH-Information				UL-EDCH-Information-r8				OPTIONAL,
		dl-HSPDSCH-Information			DL-HSPDSCH-Information-r8			OPTIONAL,
		dl-CommonInformation			DL-CommonInformation-r8				OPTIONAL,
		dl-InformationPerRL-List		DL-InformationPerRL-List-r8			OPTIONAL,
		dl-SecondaryCellInfoFDD			DL-SecondaryCellInfoFDD				OPTIONAL,
		controlChannelDRXInfo-TDD128	ControlChannelDRXInfo-TDD128-r8		OPTIONAL,
		sps-Information-TDD128			SPS-Information-TDD128-r8			OPTIONAL,
	-- MBMS IEs
		mbms-PL-ServiceRestrictInfo		MBMS-PL-ServiceRestrictInfo-r6		OPTIONAL,
		mbms-RB-ListReleasedToChangeTransferMode
										RB-InformationReleaseList			OPTIONAL
}

RadioBearerRelease-v890ext-IEs ::= SEQUENCE {
	-- Physical channel IEs
		dl-SecondaryCellInfoFDD-v890ext		DL-SecondaryCellInfoFDD-v890ext		OPTIONAL,
		dl-HSPDSCH-Information				DL-HSPDSCH-Information-r8-ext		OPTIONAL
}

RadioBearerRelease-v8a0ext-IEs ::= SEQUENCE {
	-- Physical channel IEs
		dl-HSPDSCH-Information				DL-HSPDSCH-Information-r8-ext2		OPTIONAL
}

RadioBearerRelease-r9-IEs ::= SEQUENCE {
	-- User equipment IEs
		integrityProtectionModeInfo		IntegrityProtectionModeInfo-r7		OPTIONAL,
		cipheringModeInfo				CipheringModeInfo-r7				OPTIONAL,
		activationTime					ActivationTime						OPTIONAL,
		new-U-RNTI						U-RNTI								OPTIONAL,
		new-C-RNTI						C-RNTI								OPTIONAL,
		-- The IE "new-DSCH-RNTI" should not be included in FDD mode,
		-- and if received the UE behaviour is unspecified
		new-DSCH-RNTI					DSCH-RNTI							OPTIONAL,
		new-H-RNTI						H-RNTI								OPTIONAL,
		newPrimary-E-RNTI				E-RNTI								OPTIONAL,
		newSecondary-E-RNTI				E-RNTI								OPTIONAL,
		rrc-StateIndicator				RRC-StateIndicator,
		ueMobilityStateIndicator		High-MobilityDetected				OPTIONAL,
		utran-DRX-CycleLengthCoeff		UTRAN-DRX-CycleLengthCoefficient-r7	OPTIONAL,
	-- Core network IEs
		cn-InformationInfo				CN-InformationInfo-r6				OPTIONAL,
		signallingConnectionRelIndication	CN-DomainIdentity				OPTIONAL,
	-- UTRAN mobility IEs
		ura-Identity					URA-Identity						OPTIONAL,
		supportForChangeOfUE-Capability	BOOLEAN								OPTIONAL,
	-- Radio bearer IEs
		rab-InformationReconfigList		RAB-InformationReconfigList-r8		OPTIONAL,
		rb-InformationReleaseList		RB-InformationReleaseList,
		rb-InformationReconfigList		RB-InformationReconfigList-r8		OPTIONAL,
		rb-InformationAffectedList		RB-InformationAffectedList-r8		OPTIONAL,
		dl-CounterSynchronisationInfo	DL-CounterSynchronisationInfo-r5	OPTIONAL,
	-- Transport channel IEs
		ul-CommonTransChInfo			UL-CommonTransChInfo-r4				OPTIONAL,
		ul-deletedTransChInfoList		UL-DeletedTransChInfoList-r6		OPTIONAL,
		ul-AddReconfTransChInfoList		UL-AddReconfTransChInfoList-r8		OPTIONAL,
		dl-CommonTransChInfo			DL-CommonTransChInfo-r4				OPTIONAL,
		dl-DeletedTransChInfoList		DL-DeletedTransChInfoList-r7		OPTIONAL,
		dl-AddReconfTransChInfoList		DL-AddReconfTransChInfoList-r9		OPTIONAL,
	-- Physical channel IEs
		frequencyInfo					FrequencyInfo						OPTIONAL,
		multi-frequencyInfo				Multi-frequencyInfo-LCR-r7			OPTIONAL,
		dtx-drx-TimingInfo				DTX-DRX-TimingInfo-r7				OPTIONAL,
		dtx-drx-Info					DTX-DRX-Info-r7						OPTIONAL,
		hs-scch-LessInfo				HS-SCCH-LessInfo-r7					OPTIONAL,
		mimoParameters					MIMO-Parameters-r9					OPTIONAL,
		maxAllowedUL-TX-Power			MaxAllowedUL-TX-Power				OPTIONAL,
		ul-DPCH-Info					UL-DPCH-Info-r7						OPTIONAL,
		ul-EDCH-Information				UL-EDCH-Information-r9				OPTIONAL,
		ul-SecondaryCellInfoFDD			UL-SecondaryCellInfoFDD				OPTIONAL,
		dl-HSPDSCH-Information			DL-HSPDSCH-Information-r9			OPTIONAL,
		dl-CommonInformation			DL-CommonInformation-r8				OPTIONAL,
		dl-InformationPerRL-List		DL-InformationPerRL-List-r8			OPTIONAL,
		dl-SecondaryCellInfoFDD			DL-SecondaryCellInfoFDD-r9			OPTIONAL,
		controlChannelDRXInfo-TDD128	ControlChannelDRXInfo-TDD128-r8		OPTIONAL,
		sps-Information-TDD128			SPS-Information-TDD128-r8			OPTIONAL,
	-- MBMS IEs
		mbms-PL-ServiceRestrictInfo		MBMS-PL-ServiceRestrictInfo-r6		OPTIONAL,
		mbms-RB-ListReleasedToChangeTransferMode
										RB-InformationReleaseList			OPTIONAL
}

RadioBearerRelease-v950ext-IEs ::= SEQUENCE {
	-- Physical channel IEs
		secondaryCellMimoParameters		SecondaryCellMIMOparametersFDD-v950ext		OPTIONAL
}

RadioBearerRelease-v970ext-IEs ::= SEQUENCE {
	-- Measurement IEs for LCR
		cellDCHMeasOccasionInfo-TDD128	CellDCHMeasOccasionInfo-TDD128-r9	OPTIONAL
}

RadioBearerRelease-v9c0ext-IEs ::= SEQUENCE {
	-- For 1.28Mcps TDD only
		dl-AddReconfTransChInfoList		DL-AddReconfTransChInfoList-TDD128-v9c0ext			OPTIONAL
}

RadioBearerRelease-r10-IEs ::= SEQUENCE {
	-- User equipment IEs
		integrityProtectionModeInfo		IntegrityProtectionModeInfo-r7		OPTIONAL,
		cipheringModeInfo				CipheringModeInfo-r7				OPTIONAL,
		activationTime					ActivationTime						OPTIONAL,
		new-U-RNTI						U-RNTI								OPTIONAL,
		new-C-RNTI						C-RNTI								OPTIONAL,
		-- The IE "new-DSCH-RNTI" should not be included in FDD mode,
		-- and if received the UE behaviour is unspecified
		new-DSCH-RNTI					DSCH-RNTI							OPTIONAL,
		new-H-RNTI						H-RNTI								OPTIONAL,
		newPrimary-E-RNTI				E-RNTI								OPTIONAL,
		newSecondary-E-RNTI				E-RNTI								OPTIONAL,
		rrc-StateIndicator				RRC-StateIndicator,
		ueMobilityStateIndicator		High-MobilityDetected				OPTIONAL,
		utran-DRX-CycleLengthCoeff		UTRAN-DRX-CycleLengthCoefficient-r7	OPTIONAL,
	-- Core network IEs
		cn-InformationInfo				CN-InformationInfo-r6				OPTIONAL,
		signallingConnectionRelIndication	CN-DomainIdentity				OPTIONAL,
	-- UTRAN mobility IEs
		ura-Identity					URA-Identity						OPTIONAL,
		supportForChangeOfUE-Capability	BOOLEAN								OPTIONAL,
	-- Radio bearer IEs
		rab-InformationReconfigList		RAB-InformationReconfigList-r8		OPTIONAL,
		rb-InformationReleaseList		RB-InformationReleaseList,
		rb-InformationReconfigList		RB-InformationReconfigList-r8		OPTIONAL,
		rb-InformationAffectedList		RB-InformationAffectedList-r8		OPTIONAL,
		dl-CounterSynchronisationInfo	DL-CounterSynchronisationInfo-r5	OPTIONAL,
	-- Transport channel IEs
		ul-CommonTransChInfo			UL-CommonTransChInfo-r4				OPTIONAL,
		ul-deletedTransChInfoList		UL-DeletedTransChInfoList-r6		OPTIONAL,
		ul-AddReconfTransChInfoList		UL-AddReconfTransChInfoList-r8		OPTIONAL,
		dl-CommonTransChInfo			DL-CommonTransChInfo-r4				OPTIONAL,
		dl-DeletedTransChInfoList		DL-DeletedTransChInfoList-r7		OPTIONAL,
		dl-AddReconfTransChInfoList		DL-AddReconfTransChInfoList-r9		OPTIONAL,
	-- Physical channel IEs
		frequencyInfo					FrequencyInfo						OPTIONAL,
		multi-frequencyInfo				Multi-frequencyInfo-LCR-r7			OPTIONAL,
		dtx-drx-TimingInfo				DTX-DRX-TimingInfo-r7				OPTIONAL,
		dtx-drx-Info					DTX-DRX-Info-r7						OPTIONAL,
		hs-scch-LessInfo				HS-SCCH-LessInfo-r7					OPTIONAL,
		mimoParameters					MIMO-Parameters-r9					OPTIONAL,
		maxAllowedUL-TX-Power			MaxAllowedUL-TX-Power				OPTIONAL,
		ul-DPCH-Info					UL-DPCH-Info-r7						OPTIONAL,
		ul-EDCH-Information				UL-EDCH-Information-r9				OPTIONAL,
		ul-SecondaryCellInfoFDD			UL-SecondaryCellInfoFDD				OPTIONAL,
		ul-MulticarrierEDCHInfo-TDD128	UL-MulticarrierEDCHInfo-TDD128		OPTIONAL,
		dl-HSPDSCH-Information			DL-HSPDSCH-Information-r9			OPTIONAL,
		dl-CommonInformation			DL-CommonInformation-r10			OPTIONAL,
		dl-InformationPerRL-List		DL-InformationPerRL-List-r8			OPTIONAL,
		dl-SecondaryCellInfoFDD			DL-SecondaryCellInfoFDD-r10			OPTIONAL,
		additionalDLSecCellInfoListFDD	AdditionalDLSecCellInfoListFDD		OPTIONAL,
		controlChannelDRXInfo-TDD128	ControlChannelDRXInfo-TDD128-r8		OPTIONAL,
		sps-Information-TDD128			SPS-Information-TDD128-r8			OPTIONAL,
		mu-MIMO-Info-TDD128				MU-MIMO-Info-TDD128					OPTIONAL,
	-- MBMS IEs
		mbms-PL-ServiceRestrictInfo		MBMS-PL-ServiceRestrictInfo-r6		OPTIONAL,
		mbms-RB-ListReleasedToChangeTransferMode
										RB-InformationReleaseList			OPTIONAL,
	-- Measurement IEs for LCR
		cellDCHMeasOccasionInfo-TDD128	CellDCHMeasOccasionInfo-TDD128-r9	OPTIONAL
}

RadioBearerRelease-vb50ext-IEs ::= SEQUENCE {
		ulOLTDInfoFDD						UL-OLTD-InfoFDD			OPTIONAL
}

RadioBearerRelease-r11-IEs ::= SEQUENCE {
	-- User equipment IEs
		integrityProtectionModeInfo		IntegrityProtectionModeInfo-r7		OPTIONAL,
		cipheringModeInfo				CipheringModeInfo-r7				OPTIONAL,
		activationTime					ActivationTime						OPTIONAL,
		new-U-RNTI						U-RNTI								OPTIONAL,
		new-C-RNTI						C-RNTI								OPTIONAL,
		-- The IE "new-DSCH-RNTI" should not be included in FDD mode,
		-- and if received the UE behaviour is unspecified
		new-DSCH-RNTI					DSCH-RNTI							OPTIONAL,
		new-H-RNTI						H-RNTI								OPTIONAL,
		newPrimary-E-RNTI				E-RNTI								OPTIONAL,
		newSecondary-E-RNTI				E-RNTI								OPTIONAL,
		rrc-StateIndicator				RRC-StateIndicator,
		ueMobilityStateIndicator		High-MobilityDetected				OPTIONAL,
		utran-DRX-CycleLengthCoeff		UTRAN-DRX-CycleLengthCoefficient-r7	OPTIONAL,
	-- Core network IEs
		cn-InformationInfo				CN-InformationInfo-r6				OPTIONAL,
		signallingConnectionRelIndication	CN-DomainIdentity				OPTIONAL,
	-- UTRAN mobility IEs
		ura-Identity					URA-Identity						OPTIONAL,
		supportForChangeOfUE-Capability	BOOLEAN								OPTIONAL,
	-- Radio bearer IEs
		rab-InformationReconfigList		RAB-InformationReconfigList-r8		OPTIONAL,
		rb-InformationReleaseList		RB-InformationReleaseList,
		rb-InformationReconfigList		RB-InformationReconfigList-r11		OPTIONAL,
		rb-InformationAffectedList		RB-InformationAffectedList-r8		OPTIONAL,
		dl-CounterSynchronisationInfo	DL-CounterSynchronisationInfo-r5	OPTIONAL,
	-- Transport channel IEs
		ul-CommonTransChInfo			UL-CommonTransChInfo-r4				OPTIONAL,
		ul-deletedTransChInfoList		UL-DeletedTransChInfoList-r6		OPTIONAL,
		ul-AddReconfTransChInfoList		UL-AddReconfTransChInfoList-r8		OPTIONAL,
		dl-CommonTransChInfo			DL-CommonTransChInfo-r4				OPTIONAL,
		dl-DeletedTransChInfoList		DL-DeletedTransChInfoList-r7		OPTIONAL,
		dl-AddReconfTransChInfoList		DL-AddReconfTransChInfoList-r11		OPTIONAL,
	-- Physical channel IEs
		frequencyInfo					FrequencyInfo						OPTIONAL,
		multi-frequencyInfo				Multi-frequencyInfo-LCR-r7			OPTIONAL,
		dtx-drx-TimingInfo				DTX-DRX-TimingInfo-r7				OPTIONAL,
		dtx-drx-Info					DTX-DRX-Info-r7						OPTIONAL,
		hs-scch-LessInfo				HS-SCCH-LessInfo-r7					OPTIONAL,
		mimoParameters					MIMO-Parameters-r9					OPTIONAL,
		mimo4x4Parameters				MIMO4x4-Parameters					OPTIONAL,
		maxAllowedUL-TX-Power			MaxAllowedUL-TX-Power				OPTIONAL,
		ul-DPCH-Info					UL-DPCH-Info-r11						OPTIONAL,
		ul-EDCH-Information				UL-EDCH-Information-r11				OPTIONAL,
		ul-SecondaryCellInfoFDD			UL-SecondaryCellInfoFDD				OPTIONAL,
		ul-MulticarrierEDCHInfo-TDD128	UL-MulticarrierEDCHInfo-TDD128		OPTIONAL,
		ul-CLTD-InfoFDD					UL-CLTD-InfoFDD						OPTIONAL,
		ul-OLTD-InfoFDD					UL-OLTD-InfoFDD						OPTIONAL,
		dl-HSPDSCH-Information			DL-HSPDSCH-Information-r11			OPTIONAL,
		dl-CommonInformation			DL-CommonInformation-r11			OPTIONAL,
		dl-InformationPerRL-List		DL-InformationPerRL-List-r11			OPTIONAL,
		dl-SecondaryCellInfoFDD			DL-SecondaryCellInfoFDD-r11			OPTIONAL,
		additionalDLSecCellInfoListFDD	AdditionalDLSecCellInfoListFDD-r11	OPTIONAL,
		additionalDLSecCellInfoListFDD2	AdditionalDLSecCellInfoListFDD2		OPTIONAL,
		commonERGCHInfoFDD				CommonERGCHInfoFDD					OPTIONAL,
		controlChannelDRXInfo-TDD128	ControlChannelDRXInfo-TDD128-r8		OPTIONAL,
		sps-Information-TDD128			SPS-Information-TDD128-r8			OPTIONAL,
		mu-MIMO-Info-TDD128				MU-MIMO-Info-TDD128					OPTIONAL,
	-- MBMS IEs
		mbms-PL-ServiceRestrictInfo		MBMS-PL-ServiceRestrictInfo-r6		OPTIONAL,
		mbms-RB-ListReleasedToChangeTransferMode
										RB-InformationReleaseList			OPTIONAL,
	-- Measurement IEs for LCR
		cellDCHMeasOccasionInfo-TDD128	CellDCHMeasOccasionInfo-TDD128-r9	OPTIONAL
}

-- ***************************************************
--
-- RADIO BEARER RELEASE COMPLETE
--
-- ***************************************************

RadioBearerReleaseComplete ::= SEQUENCE {
	-- User equipment IEs
		rrc-TransactionIdentifier		RRC-TransactionIdentifier,
		ul-IntegProtActivationInfo		IntegrityProtActivationInfo			OPTIONAL,
		-- TABULAR: UL-TimingAdvance is applicable for TDD mode only.
		ul-TimingAdvance				UL-TimingAdvance					OPTIONAL,
	-- Radio bearer IEs
		count-C-ActivationTime			ActivationTime						OPTIONAL,
		-- dummy is not used in this version of the specification and
		-- it should be ignored by the receiver.
		dummy							RB-ActivationTimeInfoList			OPTIONAL,
		ul-CounterSynchronisationInfo	UL-CounterSynchronisationInfo		OPTIONAL,
		laterNonCriticalExtensions		SEQUENCE {
			-- Container for additional R99 extensions
			radioBearerReleaseComplete-r3-add-ext		BIT STRING		OPTIONAL,
			v770NonCriticalExtensions		SEQUENCE {
				radioBearerReleaseComplete-v770ext
												RadioBearerReleaseComplete-v770ext-IEs,
				nonCriticalExtensions			SEQUENCE {}		OPTIONAL
			}	OPTIONAL
		}	OPTIONAL
}

RadioBearerReleaseComplete-v770ext-IEs ::= SEQUENCE {
		-- TABULAR: EXT-UL-TimingAdvance is applicable for TDD mode only.
		ext-UL-TimingAdvance					EXT-UL-TimingAdvance	OPTIONAL,
		deferredMeasurementControlReading		ENUMERATED { true }		OPTIONAL
}

-- ***************************************************
--
-- RADIO BEARER RELEASE FAILURE
--
-- ***************************************************

RadioBearerReleaseFailure ::= SEQUENCE {
	-- User equipment IEs
		rrc-TransactionIdentifier		RRC-TransactionIdentifier,
		failureCause					FailureCauseWithProtErr,
	-- Radio bearer IEs
		potentiallySuccesfulBearerList	RB-IdentityList						OPTIONAL,
		laterNonCriticalExtensions		SEQUENCE {
			-- Container for additional R99 extensions
			radioBearerReleaseFailure-r3-add-ext		BIT STRING		OPTIONAL,
			nonCriticalExtensions			SEQUENCE {}		OPTIONAL
		}	OPTIONAL
}

-- ***************************************************
--
-- RADIO BEARER SETUP
--
-- ***************************************************

RadioBearerSetup ::= CHOICE {
	r3								SEQUENCE {
		radioBearerSetup-r3				RadioBearerSetup-r3-IEs,
		v3a0NonCriticalExtensions		SEQUENCE {
			radioBearerSetup-v3a0ext		RadioBearerSetup-v3a0ext,
			laterNonCriticalExtensions		SEQUENCE {
				-- Container for additional R99 extensions
				radioBearerSetup-r3-add-ext		BIT STRING		OPTIONAL,
				v4b0NonCriticalExtensions		SEQUENCE {
					radioBearerSetup-v4b0ext		RadioBearerSetup-v4b0ext-IEs,
					v590NonCriticalExtensions		SEQUENCE {
						radioBearerSetup-v590ext		RadioBearerSetup-v590ext-IEs,
						v5d0NonCriticalExtenstions		SEQUENCE {
							radioBearerSetup-v5d0ext		RadioBearerSetup-v5d0ext-IEs,
							v690NonCriticalExtensions		SEQUENCE {
								radioBearerSetup-v690ext		RadioBearerSetup-v690ext-IEs,
								nonCriticalExtensions			SEQUENCE {} OPTIONAL
							}	OPTIONAL
						}	OPTIONAL
					}	OPTIONAL
				}	OPTIONAL
			}	OPTIONAL
		}	OPTIONAL
	},
	later-than-r3					SEQUENCE {
		rrc-TransactionIdentifier		RRC-TransactionIdentifier,
		criticalExtensions				CHOICE {
			r4								SEQUENCE {
				radioBearerSetup-r4				RadioBearerSetup-r4-IEs,
				v4d0NonCriticalExtensions			SEQUENCE {
					-- Container for adding non critical extensions after freezing REL-5
					radioBearerSetup-r4-add-ext		BIT STRING		OPTIONAL,
					v590NonCriticalExtensions		SEQUENCE {
						radioBearerSetup-v590ext		RadioBearerSetup-v590ext-IEs,
						v5d0NonCriticalExtenstions		SEQUENCE {
							radioBearerSetup-v5d0ext		RadioBearerSetup-v5d0ext-IEs,
							v690NonCriticalExtensions		SEQUENCE {
								radioBearerSetup-v690ext		RadioBearerSetup-v690ext-IEs,
								nonCriticalExtensions			SEQUENCE {}		OPTIONAL
							}	OPTIONAL
						}	OPTIONAL
					}	OPTIONAL
				}	OPTIONAL
			},
			criticalExtensions				CHOICE {
				r5								SEQUENCE {
					radioBearerSetup-r5				RadioBearerSetup-r5-IEs,
					-- Container for adding non critical extensions after freezing REL-6
					radioBearerSetup-r5-add-ext		BIT STRING		OPTIONAL,
					v5d0NonCriticalExtenstions		SEQUENCE {
						radioBearerSetup-v5d0ext		RadioBearerSetup-v5d0ext-IEs,
						v690NonCriticalExtensions		SEQUENCE {
							radioBearerSetup-v690ext		RadioBearerSetup-v690ext-IEs,
							nonCriticalExtensions			SEQUENCE {}		OPTIONAL
						}	OPTIONAL
					}	OPTIONAL
				},
				criticalExtensions				CHOICE {
					r6								SEQUENCE {
						radioBearerSetup-r6				RadioBearerSetup-r6-IEs,
						-- Container for adding non critical extensions after freezing REL-7
						radioBearerSetup-r6-add-ext		BIT STRING		OPTIONAL,
						v6b0NonCriticalExtensions		SEQUENCE {
							radioBearerSetup-v6b0ext		RadioBearerSetup-v6b0ext-IEs,
							nonCriticalExtensions			SEQUENCE {}		OPTIONAL
						}	OPTIONAL
					},
					criticalExtensions				CHOICE {
						r7								SEQUENCE {
							radioBearerSetup-r7				RadioBearerSetup-r7-IEs,
							-- Container for adding non critical extensions after freezing REL-8
							radioBearerSetup-r7-add-ext		BIT STRING
										(CONTAINING RadioBearerSetup-r7-add-ext-IEs)	OPTIONAL,
							v780NonCriticalExtensions		SEQUENCE {
								radioBearerSetup-v780ext		RadioBearerSetup-v780ext-IEs,
								v820NonCriticalExtensions		SEQUENCE {
									radioBearerSetup-v820ext		RadioBearerSetup-v820ext-IEs,
									nonCriticalExtensions			SEQUENCE {}		OPTIONAL
								}	OPTIONAL
							}	OPTIONAL
						},
						criticalExtensions				CHOICE {
							r8								SEQUENCE {
								radioBearerSetup-r8				RadioBearerSetup-r8-IEs,
								-- Container for adding non critical extensions after freezing REL-9
								radioBearerSetup-r8-add-ext		BIT STRING		OPTIONAL,
								v7d0NonCriticalExtensions		SEQUENCE {
									radioBearerSetup-v7d0ext		RadioBearerSetup-v7d0ext-IEs,
									v7f0NonCriticalExtensions		SEQUENCE {
										radioBearerSetup-v7f0ext	RadioBearerSetup-v7f0ext-IEs,
										v890NonCriticalExtensions		SEQUENCE {
											radioBearerSetup-v890ext
																	RadioBearerSetup-v890ext-IEs,
											v7g0NonCriticalExtensions		SEQUENCE {
												radioBearerSetup-v7g0ext
																	RadioBearerSetup-v7g0ext-IEs,
												v8a0NonCriticalExtensions		SEQUENCE {
													radioBearerSetup-v8a0ext
																	RadioBearerSetup-v8a0ext-IEs,
													nonCriticalExtensions
																	SEQUENCE {}		OPTIONAL
												}	OPTIONAL
											}	OPTIONAL
										}	OPTIONAL
									}	OPTIONAL
								}	OPTIONAL
							},
							criticalExtensions				CHOICE {
								r9								SEQUENCE {
									radioBearerSetup-r9				RadioBearerSetup-r9-IEs,
									-- Container for adding non critical extensions after 
									-- freezing REL-10
									radioBearerSetup-r9-add-ext		BIT STRING		OPTIONAL,
									v950NonCriticalExtensions		SEQUENCE {
										radioBearerSetup-v950ext		RadioBearerSetup-v950ext-IEs,
										v9c0NonCriticalExtensions		SEQUENCE {
											radioBearerSetup-v9c0ext		RadioBearerSetup-v9c0ext-IEs,
											nonCriticalExtensions			SEQUENCE {}		OPTIONAL
										}	OPTIONAL
									}	OPTIONAL
								},
								criticalExtensions				CHOICE {
									r10								SEQUENCE {
										radioBearerSetup-r10			RadioBearerSetup-r10-IEs,
										-- Container for adding non critical extensions after 
										-- freezing REL-11
										radioBearerSetup-r10-add-ext	BIT STRING		OPTIONAL,
										v9c0NonCriticalExtensions		SEQUENCE {
											radioBearerSetup-v9c0ext		RadioBearerSetup-v9c0ext-IEs,
											vb50NonCriticalExtensions		SEQUENCE {
												radioBearerSetup-vb50ext
																	RadioBearerSetup-vb50ext-IEs,
												nonCriticalExtensions		SEQUENCE {}		OPTIONAL
											}	OPTIONAL
										}	OPTIONAL
									},
									criticalExtensions				CHOICE {
										r11								SEQUENCE {
										radioBearerSetup-r11			RadioBearerSetup-r11-IEs,
										-- Container for adding non critical extensions after 
										-- freezing REL-12
										radioBearerSetup-r11-add-ext	BIT STRING		OPTIONAL,
										nonCriticalExtensions			SEQUENCE {}		OPTIONAL
										},
										criticalExtensions				SEQUENCE {}
									}
								}
							}
						}
					}
				}
			}
		}
	}
}

RadioBearerSetup-r3-IEs ::= SEQUENCE {
	-- User equipment IEs
		rrc-TransactionIdentifier		RRC-TransactionIdentifier,
		integrityProtectionModeInfo		IntegrityProtectionModeInfo			OPTIONAL,
		cipheringModeInfo				CipheringModeInfo					OPTIONAL,
		activationTime					ActivationTime						OPTIONAL,
		new-U-RNTI						U-RNTI								OPTIONAL,
		new-C-RNTI						C-RNTI								OPTIONAL,
		rrc-StateIndicator				RRC-StateIndicator,
		utran-DRX-CycleLengthCoeff		UTRAN-DRX-CycleLengthCoefficient	OPTIONAL,
	-- UTRAN mobility IEs
		ura-Identity					URA-Identity						OPTIONAL,
	-- Core network IEs
		cn-InformationInfo				CN-InformationInfo					OPTIONAL,
	-- Radio bearer IEs
		srb-InformationSetupList		SRB-InformationSetupList			OPTIONAL,
		rab-InformationSetupList		RAB-InformationSetupList			OPTIONAL,
		rb-InformationAffectedList		RB-InformationAffectedList			OPTIONAL,
		dl-CounterSynchronisationInfo	DL-CounterSynchronisationInfo		OPTIONAL,
	-- Transport channel IEs
		ul-CommonTransChInfo			UL-CommonTransChInfo				OPTIONAL,
		ul-deletedTransChInfoList		UL-DeletedTransChInfoList			OPTIONAL,
		ul-AddReconfTransChInfoList		UL-AddReconfTransChInfoList			OPTIONAL,
		-- 'dummy', 'dummy1' and 'dummy2' are not used in this version of the specification,
		-- they should not be sent and if received they should be ignored.
		dummy							CHOICE {
			fdd								SEQUENCE {
				dummy1							CPCH-SetID					OPTIONAL,
				dummy2							DRAC-StaticInformationList	OPTIONAL
			},
			tdd								NULL
		}																	OPTIONAL,
		dl-CommonTransChInfo			DL-CommonTransChInfo				OPTIONAL,
		dl-DeletedTransChInfoList		DL-DeletedTransChInfoList			OPTIONAL,
		dl-AddReconfTransChInfoList		DL-AddReconfTransChInfoList			OPTIONAL,
	-- Physical channel IEs
		frequencyInfo					FrequencyInfo						OPTIONAL,
		maxAllowedUL-TX-Power			MaxAllowedUL-TX-Power				OPTIONAL,
		ul-ChannelRequirement			UL-ChannelRequirement				OPTIONAL,
		modeSpecificPhysChInfo			CHOICE {
			fdd								SEQUENCE {
				-- dummy is not used in this version of specification, it should
				-- not be sent and if received it should be ignored.
				dummy							DL-PDSCH-Information		OPTIONAL
			},
			tdd								NULL
		},
		dl-CommonInformation			DL-CommonInformation				OPTIONAL,
		dl-InformationPerRL-List		DL-InformationPerRL-List			OPTIONAL
}

RadioBearerSetup-v3a0ext ::= SEQUENCE {
	-- The IE "new-DSCH-RNTI" should not be included in FDD mode, and if received the UE behaviour
	-- is unspecified
	new-DSCH-RNTI					DSCH-RNTI							OPTIONAL
}

RadioBearerSetup-v4b0ext-IEs ::= SEQUENCE {
	-- Physical channel IEs
		-- dummy is not used in this version of the specification, it should
		-- not be sent and if received it should be ignored.
		dummy								SSDT-UL								OPTIONAL,
		-- The order of the RLs in IE cell-id-PerRL-List is the same as
		-- in IE DL-InformationPerRL-List included in this message
		cell-id-PerRL-List					CellIdentity-PerRL-List				OPTIONAL
}

RadioBearerSetup-v590ext-IEs ::= SEQUENCE {
	-- Physical channel IEs
		dl-TPC-PowerOffsetPerRL-List	DL-TPC-PowerOffsetPerRL-List		OPTIONAL
}

RadioBearerSetup-v5d0ext-IEs ::=	SEQUENCE {
	--Radio Bearer IEs
		pdcp-ROHC-TargetMode			PDCP-ROHC-TargetMode				OPTIONAL
}

RadioBearerSetup-r4-IEs ::= SEQUENCE {
	-- User equipment IEs
		integrityProtectionModeInfo		IntegrityProtectionModeInfo			OPTIONAL,
		cipheringModeInfo				CipheringModeInfo					OPTIONAL,
		activationTime					ActivationTime						OPTIONAL,
		new-U-RNTI						U-RNTI								OPTIONAL,
		new-C-RNTI						C-RNTI								OPTIONAL,
		-- The IE "new-DSCH-RNTI" should not be included in FDD mode, and if received
		-- the UE behaviour is unspecified
		new-DSCH-RNTI					DSCH-RNTI							OPTIONAL,
		rrc-StateIndicator				RRC-StateIndicator,
		utran-DRX-CycleLengthCoeff		UTRAN-DRX-CycleLengthCoefficient	OPTIONAL,
	-- UTRAN mobility IEs
		ura-Identity					URA-Identity						OPTIONAL,
	-- Core network IEs
		cn-InformationInfo				CN-InformationInfo					OPTIONAL,
	-- Radio bearer IEs
		srb-InformationSetupList		SRB-InformationSetupList			OPTIONAL,
		rab-InformationSetupList		RAB-InformationSetupList-r4			OPTIONAL,
		rb-InformationAffectedList		RB-InformationAffectedList			OPTIONAL,
		dl-CounterSynchronisationInfo	DL-CounterSynchronisationInfo		OPTIONAL,
	-- Transport channel IEs
		ul-CommonTransChInfo			UL-CommonTransChInfo-r4				OPTIONAL,
		ul-deletedTransChInfoList		UL-DeletedTransChInfoList			OPTIONAL,
		ul-AddReconfTransChInfoList		UL-AddReconfTransChInfoList			OPTIONAL,
		-- 'dummy', 'dummy1' and 'dummy2' are not used in this version of the specification,
		-- they should not be sent and if received they should be ignored.
		dummy							CHOICE {
			fdd								SEQUENCE {
				dummy1							CPCH-SetID					OPTIONAL,
				dummy2							DRAC-StaticInformationList	OPTIONAL
			},
			tdd								NULL
		}																	OPTIONAL,
		dl-CommonTransChInfo			DL-CommonTransChInfo-r4				OPTIONAL,
		dl-DeletedTransChInfoList		DL-DeletedTransChInfoList			OPTIONAL,
		dl-AddReconfTransChInfoList		DL-AddReconfTransChInfoList-r4		OPTIONAL,
	-- Physical channel IEs
		frequencyInfo					FrequencyInfo						OPTIONAL,
		maxAllowedUL-TX-Power			MaxAllowedUL-TX-Power				OPTIONAL,
		ul-ChannelRequirement			UL-ChannelRequirement-r4			OPTIONAL,
		modeSpecificPhysChInfo			CHOICE {
			fdd								SEQUENCE {
				-- dummy is not used in this version of specification, it should
				-- not be sent and if received it should be ignored.
				dummy							DL-PDSCH-Information		OPTIONAL
			},
			tdd								NULL
		},
		dl-CommonInformation			DL-CommonInformation-r4				OPTIONAL,
		dl-InformationPerRL-List		DL-InformationPerRL-List-r4			OPTIONAL
}

RadioBearerSetup-r5-IEs ::= SEQUENCE {
	-- User equipment IEs
		integrityProtectionModeInfo		IntegrityProtectionModeInfo			OPTIONAL,
		cipheringModeInfo				CipheringModeInfo					OPTIONAL,
		activationTime					ActivationTime						OPTIONAL,
		new-U-RNTI						U-RNTI								OPTIONAL,
		new-C-RNTI						C-RNTI								OPTIONAL,
		-- The IE "new-DSCH-RNTI" should not be included in FDD mode, and if received
		-- the UE behaviour is unspecified
		new-DSCH-RNTI					DSCH-RNTI							OPTIONAL,
		new-H-RNTI						H-RNTI								OPTIONAL,
		rrc-StateIndicator				RRC-StateIndicator,
		utran-DRX-CycleLengthCoeff		UTRAN-DRX-CycleLengthCoefficient	OPTIONAL,
	-- UTRAN mobility IEs
		ura-Identity					URA-Identity						OPTIONAL,
	-- Core network IEs
		cn-InformationInfo				CN-InformationInfo					OPTIONAL,
	-- Radio bearer IEs
		srb-InformationSetupList		SRB-InformationSetupList-r5			OPTIONAL,
		rab-InformationSetupList		RAB-InformationSetupList-r5			OPTIONAL,
		rb-InformationAffectedList		RB-InformationAffectedList-r5		OPTIONAL,
		dl-CounterSynchronisationInfo	DL-CounterSynchronisationInfo-r5	OPTIONAL,
	-- Transport channel IEs
		ul-CommonTransChInfo			UL-CommonTransChInfo-r4				OPTIONAL,
		ul-deletedTransChInfoList		UL-DeletedTransChInfoList			OPTIONAL,
		ul-AddReconfTransChInfoList		UL-AddReconfTransChInfoList			OPTIONAL,
		-- 'dummy', 'dummy1' and 'dummy2' are not used in this version of the specification,
		-- they should not be sent and if received they should be ignored.
		dummy							CHOICE {
			fdd								SEQUENCE {
				dummy1							CPCH-SetID					OPTIONAL,
				dummy2							DRAC-StaticInformationList	OPTIONAL
			},
			tdd								NULL
		}																	OPTIONAL,
		dl-CommonTransChInfo			DL-CommonTransChInfo-r4				OPTIONAL,
		dl-DeletedTransChInfoList		DL-DeletedTransChInfoList-r5		OPTIONAL,
		dl-AddReconfTransChInfoList		DL-AddReconfTransChInfoList-r5		OPTIONAL,
	-- Physical channel IEs
		frequencyInfo					FrequencyInfo						OPTIONAL,
		maxAllowedUL-TX-Power			MaxAllowedUL-TX-Power				OPTIONAL,
		ul-ChannelRequirement			UL-ChannelRequirement-r5			OPTIONAL,
		modeSpecificPhysChInfo			CHOICE {
			fdd								SEQUENCE {
				-- dummy is not used in this version of specification, it should
				-- not be sent and if received it should be ignored.
				dummy							DL-PDSCH-Information		OPTIONAL
			},
			tdd								NULL
		},
		dl-HSPDSCH-Information			DL-HSPDSCH-Information				OPTIONAL,
		dl-CommonInformation			DL-CommonInformation-r5				OPTIONAL,
		dl-InformationPerRL-List		DL-InformationPerRL-List-r5			OPTIONAL
}

RadioBearerSetup-v690ext-IEs ::= SEQUENCE {
	-- Core network IEs
		primary-plmn-Identity			PLMN-Identity						OPTIONAL,
	-- Physical channel IEs
		-- The IE harq-Preamble-Mode should not be used in the r3 and r4 versions of the message
		-- If included in the r3 or r4 version of the message, the UE should ignore the IE
		harq-Preamble-Mode				HARQ-Preamble-Mode					OPTIONAL,
		beaconPLEst						BEACON-PL-Est						OPTIONAL,
		postVerificationPeriod			ENUMERATED { true }					OPTIONAL,
		dhs-sync						DHS-Sync							OPTIONAL,
		timingMaintainedSynchInd		TimingMaintainedSynchInd			OPTIONAL,
	-- Radio bearer IEs
		rab-InformationSetupList		RAB-InformationSetupList-r6-ext		OPTIONAL,
	-- MBMS IEs
		mbms-PL-ServiceRestrictInfo		MBMS-PL-ServiceRestrictInfo-r6		OPTIONAL
}

RadioBearerSetup-r6-IEs ::= SEQUENCE {
	-- User equipment IEs
		integrityProtectionModeInfo		IntegrityProtectionModeInfo			OPTIONAL,
		cipheringModeInfo				CipheringModeInfo					OPTIONAL,
		activationTime					ActivationTime						OPTIONAL,
		new-U-RNTI						U-RNTI								OPTIONAL,
		new-C-RNTI						C-RNTI								OPTIONAL,
		-- The IE "new-DSCH-RNTI" should not be included in FDD mode,
		-- and if received the UE behaviour is unspecified
		new-DSCH-RNTI					DSCH-RNTI							OPTIONAL,
		new-H-RNTI						H-RNTI								OPTIONAL,
		newPrimary-E-RNTI				E-RNTI								OPTIONAL,
		newSecondary-E-RNTI				E-RNTI								OPTIONAL,
		rrc-StateIndicator				RRC-StateIndicator,
		utran-DRX-CycleLengthCoeff		UTRAN-DRX-CycleLengthCoefficient	OPTIONAL,
	-- UTRAN mobility IEs
		ura-Identity					URA-Identity						OPTIONAL,
	-- Core network IEs
		cn-InformationInfo				CN-InformationInfo-r6				OPTIONAL,
		specificationMode				CHOICE {
			complete						SEQUENCE {
			-- Radio bearer IEs
				srb-InformationSetupList		SRB-InformationSetupList-r6			OPTIONAL,
				rab-InformationSetupList		RAB-InformationSetupList-r6			OPTIONAL,
				rab-InformationReconfigList		RAB-InformationReconfigList			OPTIONAL,
				rb-InformationReconfigList		RB-InformationReconfigList-r6		OPTIONAL,
				rb-InformationAffectedList		RB-InformationAffectedList-r6		OPTIONAL,
				dl-CounterSynchronisationInfo	DL-CounterSynchronisationInfo-r5	OPTIONAL,
				pdcp-ROHC-TargetMode			PDCP-ROHC-TargetMode				OPTIONAL,
			-- Transport channel IEs
				ul-CommonTransChInfo			UL-CommonTransChInfo-r4				OPTIONAL,
				ul-deletedTransChInfoList		UL-DeletedTransChInfoList-r6		OPTIONAL,
				ul-AddReconfTransChInfoList		UL-AddReconfTransChInfoList-r6		OPTIONAL,
				dl-CommonTransChInfo			DL-CommonTransChInfo-r4				OPTIONAL,
				dl-DeletedTransChInfoList		DL-DeletedTransChInfoList-r5		OPTIONAL,
				dl-AddReconfTransChInfoList		DL-AddReconfTransChInfoList-r5		OPTIONAL
			},
			-- dummy is not used in this version of the specification
			-- if it is sent, the UE behaviour is unspecified.
			dummy							SEQUENCE {
				rab-Info						RAB-Info-r6,
				defaultConfigMode				DefaultConfigMode,
				defaultConfigIdentity 			DefaultConfigIdentity-r6,
				rb-InformationChangedList		RB-InformationChangedList-r6		OPTIONAL,
				powerOffsetInfoShort			PowerOffsetInfoShort
			}
		},
	-- Physical channel IEs
		frequencyInfo					FrequencyInfo						OPTIONAL,
		maxAllowedUL-TX-Power			MaxAllowedUL-TX-Power				OPTIONAL,
		ul-DPCH-Info					UL-DPCH-Info-r6						OPTIONAL,
		ul-EDCH-Information				UL-EDCH-Information-r6				OPTIONAL,
		dl-HSPDSCH-Information			DL-HSPDSCH-Information-r6			OPTIONAL,
		dl-CommonInformation			DL-CommonInformation-r6				OPTIONAL,
		dl-InformationPerRL-List		DL-InformationPerRL-List-r6			OPTIONAL,
	-- MBMS IEs
		mbms-PL-ServiceRestrictInfo		MBMS-PL-ServiceRestrictInfo-r6		OPTIONAL
}

RadioBearerSetup-v6b0ext-IEs ::= SEQUENCE {
	-- Physical channel IEs
		dl-InformationPerRL-List-v6b0ext	DL-InformationPerRL-List-v6b0ext	OPTIONAL,
	-- MBMS IEs
		-- The order of the RABs in IE rab-InformationSetupListExt is the same as
		-- in IE rab-InformationSetupList that is included in this message
		rab-InformationSetupListExt		RAB-InformationSetupList-v6b0ext	OPTIONAL
}

RadioBearerSetup-r7-IEs ::= SEQUENCE {
	-- User equipment IEs
		integrityProtectionModeInfo		IntegrityProtectionModeInfo-r7		OPTIONAL,
		cipheringModeInfo				CipheringModeInfo-r7				OPTIONAL,
		activationTime					ActivationTime						OPTIONAL,
		new-U-RNTI						U-RNTI								OPTIONAL,
		new-C-RNTI						C-RNTI								OPTIONAL,
		-- The IE "new-DSCH-RNTI" should not be included in FDD mode,
		-- and if received the UE behaviour is unspecified
		new-DSCH-RNTI					DSCH-RNTI							OPTIONAL,
		new-H-RNTI						H-RNTI								OPTIONAL,
		newPrimary-E-RNTI				E-RNTI								OPTIONAL,
		newSecondary-E-RNTI				E-RNTI								OPTIONAL,
		rrc-StateIndicator				RRC-StateIndicator,
		utran-DRX-CycleLengthCoeff		UTRAN-DRX-CycleLengthCoefficient-r7	OPTIONAL,
	-- UTRAN mobility IEs
		ura-Identity					URA-Identity						OPTIONAL,
		supportForChangeOfUE-Capability	BOOLEAN								OPTIONAL,
	-- Core network IEs
		cn-InformationInfo				CN-InformationInfo-r6				OPTIONAL,
		specificationMode				CHOICE {
			complete						SEQUENCE {
			-- Radio bearer IEs
				srb-InformationSetupList		SRB-InformationSetupList-r7			OPTIONAL,
				rab-InformationSetupList		RAB-InformationSetupList-r7			OPTIONAL,
				rab-InformationReconfigList		RAB-InformationReconfigList			OPTIONAL,
				rb-InformationReconfigList		RB-InformationReconfigList-r7		OPTIONAL,
				rb-InformationAffectedList		RB-InformationAffectedList-r7		OPTIONAL,
				dl-CounterSynchronisationInfo	DL-CounterSynchronisationInfo-r5	OPTIONAL,
				pdcp-ROHC-TargetMode			PDCP-ROHC-TargetMode				OPTIONAL,
			-- Transport channel IEs
				ul-CommonTransChInfo			UL-CommonTransChInfo-r4				OPTIONAL,
				ul-deletedTransChInfoList		UL-DeletedTransChInfoList-r6		OPTIONAL,
				ul-AddReconfTransChInfoList		UL-AddReconfTransChInfoList-r7		OPTIONAL,
				dl-CommonTransChInfo			DL-CommonTransChInfo-r4				OPTIONAL,
				dl-DeletedTransChInfoList		DL-DeletedTransChInfoList-r7		OPTIONAL,
				dl-AddReconfTransChInfoList		DL-AddReconfTransChInfoList-r7		OPTIONAL
			},
			-- dummy is not used in this version of the specification
			-- if it is sent, the UE behaviour is unspecified.
			dummy							NULL
		},
	-- Physical channel IEs
		frequencyInfo					FrequencyInfo						OPTIONAL,
		multi-frequencyInfo				Multi-frequencyInfo-LCR-r7			OPTIONAL,
		dtx-drx-TimingInfo				DTX-DRX-TimingInfo-r7				OPTIONAL,
		dtx-drx-Info					DTX-DRX-Info-r7						OPTIONAL,
		hs-scch-LessInfo				HS-SCCH-LessInfo-r7					OPTIONAL,
		mimoParameters					MIMO-Parameters-r7					OPTIONAL,
		maxAllowedUL-TX-Power			MaxAllowedUL-TX-Power				OPTIONAL,
		ul-DPCH-Info					UL-DPCH-Info-r7						OPTIONAL,
		ul-EDCH-Information				UL-EDCH-Information-r7				OPTIONAL,
		dl-HSPDSCH-Information			DL-HSPDSCH-Information-r7			OPTIONAL,
		dl-CommonInformation			DL-CommonInformation-r7				OPTIONAL,
		dl-InformationPerRL-List		DL-InformationPerRL-List-r7			OPTIONAL,
	-- MBMS IEs
		mbms-PL-ServiceRestrictInfo		MBMS-PL-ServiceRestrictInfo-r6		OPTIONAL
}

RadioBearerSetup-r7-add-ext-IEs ::= SEQUENCE {
		radioBearerSetup-v7d0ext		RadioBearerSetup-v7d0ext-IEs		OPTIONAL,
		v7f0NonCriticalExtensions		SEQUENCE {
			radioBearerSetup-v7f0ext			RadioBearerSetup-v7f0ext-IEs,
			v7g0NonCriticalExtensions		SEQUENCE {
				radioBearerSetup-v7g0ext			RadioBearerSetup-v7g0ext-IEs,
				nonCriticalExtensions			SEQUENCE {}		OPTIONAL
			}	OPTIONAL
		}	OPTIONAL
}

RadioBearerSetup-v780ext-IEs ::= SEQUENCE {
	-- Physical channel IEs
		hs-DSCH-TBSizeTable				HS-DSCH-TBSizeTable					OPTIONAL
}

RadioBearerSetup-v7d0ext-IEs ::= SEQUENCE {
	-- Physical channel IEs
		ul-EDCH-Information				UL-EDCH-Information-ext				OPTIONAL
}

RadioBearerSetup-v7f0ext-IEs ::= SEQUENCE {
	-- Physical channel IEs
	mimoParameters						MIMO-Parameters-v7f0ext				OPTIONAL
}

RadioBearerSetup-v7g0ext-IEs ::= SEQUENCE {
	-- Physical channel IEs
	mimoParameters						MIMO-Parameters-v7g0ext				OPTIONAL
}

RadioBearerSetup-r8-IEs ::= SEQUENCE {
	-- User equipment IEs
		integrityProtectionModeInfo		IntegrityProtectionModeInfo-r7		OPTIONAL,
		cipheringModeInfo				CipheringModeInfo-r7				OPTIONAL,
		sr-vcc-Info						SR-VCC-Info							OPTIONAL,
		activationTime					ActivationTime						OPTIONAL,
		new-U-RNTI						U-RNTI								OPTIONAL,
		new-C-RNTI						C-RNTI								OPTIONAL,
		-- The IE "new-DSCH-RNTI" should not be included in FDD mode,
		-- and if received the UE behaviour is unspecified
		new-DSCH-RNTI					DSCH-RNTI							OPTIONAL,
		new-H-RNTI						H-RNTI								OPTIONAL,
		newPrimary-E-RNTI				E-RNTI								OPTIONAL,
		newSecondary-E-RNTI				E-RNTI								OPTIONAL,
		rrc-StateIndicator				RRC-StateIndicator,
		utran-DRX-CycleLengthCoeff		UTRAN-DRX-CycleLengthCoefficient-r7	OPTIONAL,
	-- UTRAN mobility IEs
		ura-Identity					URA-Identity						OPTIONAL,
		supportForChangeOfUE-Capability	BOOLEAN								OPTIONAL,
	-- Core network IEs
		cn-InformationInfo				CN-InformationInfo-r6				OPTIONAL,
	-- Radio bearer IEs
		srb-InformationSetupList		SRB-InformationSetupList-r8			OPTIONAL,
		rab-InformationSetupList		RAB-InformationSetupList-r8			OPTIONAL,
		rab-InformationReconfigList		RAB-InformationReconfigList-r8		OPTIONAL,
		rb-InformationReconfigList		RB-InformationReconfigList-r8		OPTIONAL,
		rb-InformationAffectedList		RB-InformationAffectedList-r8		OPTIONAL,
		dl-CounterSynchronisationInfo	DL-CounterSynchronisationInfo-r5	OPTIONAL,
		pdcp-ROHC-TargetMode			PDCP-ROHC-TargetMode				OPTIONAL,
	-- Transport channel IEs
		ul-CommonTransChInfo			UL-CommonTransChInfo-r4				OPTIONAL,
		ul-deletedTransChInfoList		UL-DeletedTransChInfoList-r6		OPTIONAL,
		ul-AddReconfTransChInfoList		UL-AddReconfTransChInfoList-r8		OPTIONAL,
		dl-CommonTransChInfo			DL-CommonTransChInfo-r4				OPTIONAL,
		dl-DeletedTransChInfoList		DL-DeletedTransChInfoList-r7		OPTIONAL,
		dl-AddReconfTransChInfoList		DL-AddReconfTransChInfoList-r7		OPTIONAL,
	-- Physical channel IEs
		frequencyInfo					FrequencyInfo						OPTIONAL,
		multi-frequencyInfo				Multi-frequencyInfo-LCR-r7			OPTIONAL,
		dtx-drx-TimingInfo				DTX-DRX-TimingInfo-r7				OPTIONAL,
		dtx-drx-Info					DTX-DRX-Info-r7						OPTIONAL,
		hs-scch-LessInfo				HS-SCCH-LessInfo-r7					OPTIONAL,
		mimoParameters					MIMO-Parameters-r8					OPTIONAL,
		maxAllowedUL-TX-Power			MaxAllowedUL-TX-Power				OPTIONAL,
		ul-DPCH-Info					UL-DPCH-Info-r7						OPTIONAL,
		ul-EDCH-Information				UL-EDCH-Information-r8				OPTIONAL,
		dl-HSPDSCH-Information			DL-HSPDSCH-Information-r8			OPTIONAL,
		dl-CommonInformation			DL-CommonInformation-r8				OPTIONAL,
		dl-InformationPerRL-List		DL-InformationPerRL-List-r8			OPTIONAL,
		dl-SecondaryCellInfoFDD			DL-SecondaryCellInfoFDD				OPTIONAL,
		controlChannelDRXInfo-TDD128	ControlChannelDRXInfo-TDD128-r8		OPTIONAL,
		sps-Information-TDD128			SPS-Information-TDD128-r8			OPTIONAL,
	-- MBMS IEs
		mbms-PL-ServiceRestrictInfo		MBMS-PL-ServiceRestrictInfo-r6		OPTIONAL
}

RadioBearerSetup-v820ext-IEs ::= SEQUENCE {
	-- Radio bearer IEs
		rab-InformationSetupList		RAB-InformationSetupList-v820ext	OPTIONAL
}

RadioBearerSetup-v890ext-IEs ::= SEQUENCE {
	-- Physical channel IEs
		dl-SecondaryCellInfoFDD-v890ext		DL-SecondaryCellInfoFDD-v890ext		OPTIONAL,
		dl-HSPDSCH-Information				DL-HSPDSCH-Information-r8-ext		OPTIONAL
}

RadioBearerSetup-v8a0ext-IEs ::= SEQUENCE {
	-- Physical channel IEs
		dl-HSPDSCH-Information				DL-HSPDSCH-Information-r8-ext2		OPTIONAL
}

RadioBearerSetup-r9-IEs ::= SEQUENCE {
	-- User equipment IEs
		integrityProtectionModeInfo		IntegrityProtectionModeInfo-r7		OPTIONAL,
		cipheringModeInfo				CipheringModeInfo-r7				OPTIONAL,
		sr-vcc-Info						SR-VCC-Info							OPTIONAL,
		activationTime					ActivationTime						OPTIONAL,
		new-U-RNTI						U-RNTI								OPTIONAL,
		new-C-RNTI						C-RNTI								OPTIONAL,
		-- The IE "new-DSCH-RNTI" should not be included in FDD mode,
		-- and if received the UE behaviour is unspecified
		new-DSCH-RNTI					DSCH-RNTI							OPTIONAL,
		new-H-RNTI						H-RNTI								OPTIONAL,
		newPrimary-E-RNTI				E-RNTI								OPTIONAL,
		newSecondary-E-RNTI				E-RNTI								OPTIONAL,
		rrc-StateIndicator				RRC-StateIndicator,
		utran-DRX-CycleLengthCoeff		UTRAN-DRX-CycleLengthCoefficient-r7	OPTIONAL,
	-- UTRAN mobility IEs
		ura-Identity					URA-Identity						OPTIONAL,
		supportForChangeOfUE-Capability	BOOLEAN								OPTIONAL,
	-- Core network IEs
		cn-InformationInfo				CN-InformationInfo-r6				OPTIONAL,
	-- Radio bearer IEs
		srb-InformationSetupList		SRB-InformationSetupList-r8			OPTIONAL,
		rab-InformationSetupList		RAB-InformationSetupList-r8			OPTIONAL,
		rab-InformationReconfigList		RAB-InformationReconfigList-r8		OPTIONAL,
		rb-InformationReconfigList		RB-InformationReconfigList-r8		OPTIONAL,
		rb-InformationAffectedList		RB-InformationAffectedList-r8		OPTIONAL,
		dl-CounterSynchronisationInfo	DL-CounterSynchronisationInfo-r5	OPTIONAL,
		pdcp-ROHC-TargetMode			PDCP-ROHC-TargetMode				OPTIONAL,
	-- Transport channel IEs
		ul-CommonTransChInfo			UL-CommonTransChInfo-r4				OPTIONAL,
		ul-deletedTransChInfoList		UL-DeletedTransChInfoList-r6		OPTIONAL,
		ul-AddReconfTransChInfoList		UL-AddReconfTransChInfoList-r8		OPTIONAL,
		dl-CommonTransChInfo			DL-CommonTransChInfo-r4				OPTIONAL,
		dl-DeletedTransChInfoList		DL-DeletedTransChInfoList-r7		OPTIONAL,
		dl-AddReconfTransChInfoList		DL-AddReconfTransChInfoList-r9		OPTIONAL,
	-- Physical channel IEs
		frequencyInfo					FrequencyInfo						OPTIONAL,
		multi-frequencyInfo				Multi-frequencyInfo-LCR-r7			OPTIONAL,
		dtx-drx-TimingInfo				DTX-DRX-TimingInfo-r7				OPTIONAL,
		dtx-drx-Info					DTX-DRX-Info-r7						OPTIONAL,
		hs-scch-LessInfo				HS-SCCH-LessInfo-r7					OPTIONAL,
		mimoParameters					MIMO-Parameters-r9					OPTIONAL,
		maxAllowedUL-TX-Power			MaxAllowedUL-TX-Power				OPTIONAL,
		ul-DPCH-Info					UL-DPCH-Info-r7						OPTIONAL,
		ul-EDCH-Information				UL-EDCH-Information-r9				OPTIONAL,
		ul-SecondaryCellInfoFDD			UL-SecondaryCellInfoFDD				OPTIONAL,
		dl-HSPDSCH-Information			DL-HSPDSCH-Information-r9			OPTIONAL,
		dl-CommonInformation			DL-CommonInformation-r8				OPTIONAL,
		dl-InformationPerRL-List		DL-InformationPerRL-List-r8			OPTIONAL,
		dl-SecondaryCellInfoFDD			DL-SecondaryCellInfoFDD-r9			OPTIONAL,
		controlChannelDRXInfo-TDD128	ControlChannelDRXInfo-TDD128-r8		OPTIONAL,
		sps-Information-TDD128			SPS-Information-TDD128-r8			OPTIONAL,
	-- MBMS IEs
		mbms-PL-ServiceRestrictInfo		MBMS-PL-ServiceRestrictInfo-r6		OPTIONAL,
	-- Measurement IEs for LCR
		cellDCHMeasOccasionInfo-TDD128	CellDCHMeasOccasionInfo-TDD128-r9	OPTIONAL
}

RadioBearerSetup-v950ext-IEs::= SEQUENCE {
	-- Physical channel IEs
		secondaryCellMimoParameters		SecondaryCellMIMOparametersFDD-v950ext		OPTIONAL
}

RadioBearerSetup-v9c0ext-IEs::= SEQUENCE {
	-- For 1.28Mcps TDD only
		dl-AddReconfTransChInfoList		DL-AddReconfTransChInfoList-TDD128-v9c0ext			OPTIONAL
}

RadioBearerSetup-r10-IEs ::= SEQUENCE {
	-- User equipment IEs
		integrityProtectionModeInfo		IntegrityProtectionModeInfo-r7		OPTIONAL,
		cipheringModeInfo				CipheringModeInfo-r7				OPTIONAL,
		sr-vcc-Info						SR-VCC-Info							OPTIONAL,
		activationTime					ActivationTime						OPTIONAL,
		new-U-RNTI						U-RNTI								OPTIONAL,
		new-C-RNTI						C-RNTI								OPTIONAL,
		-- The IE "new-DSCH-RNTI" should not be included in FDD mode,
		-- and if received the UE behaviour is unspecified
		new-DSCH-RNTI					DSCH-RNTI							OPTIONAL,
		new-H-RNTI						H-RNTI								OPTIONAL,
		newPrimary-E-RNTI				E-RNTI								OPTIONAL,
		newSecondary-E-RNTI				E-RNTI								OPTIONAL,
		rrc-StateIndicator				RRC-StateIndicator,
		utran-DRX-CycleLengthCoeff		UTRAN-DRX-CycleLengthCoefficient-r7	OPTIONAL,
	-- UTRAN mobility IEs
		ura-Identity					URA-Identity						OPTIONAL,
		supportForChangeOfUE-Capability	BOOLEAN								OPTIONAL,
	-- Core network IEs
		cn-InformationInfo				CN-InformationInfo-r6				OPTIONAL,
	-- Radio bearer IEs
		srb-InformationSetupList		SRB-InformationSetupList-r8			OPTIONAL,
		rab-InformationSetupList		RAB-InformationSetupList-r8			OPTIONAL,
		rab-InformationReconfigList		RAB-InformationReconfigList-r8		OPTIONAL,
		rb-InformationReconfigList		RB-InformationReconfigList-r8		OPTIONAL,
		rb-InformationAffectedList		RB-InformationAffectedList-r8		OPTIONAL,
		dl-CounterSynchronisationInfo	DL-CounterSynchronisationInfo-r5	OPTIONAL,
		pdcp-ROHC-TargetMode			PDCP-ROHC-TargetMode				OPTIONAL,
	-- Transport channel IEs
		ul-CommonTransChInfo			UL-CommonTransChInfo-r4				OPTIONAL,
		ul-deletedTransChInfoList		UL-DeletedTransChInfoList-r6		OPTIONAL,
		ul-AddReconfTransChInfoList		UL-AddReconfTransChInfoList-r8		OPTIONAL,
		dl-CommonTransChInfo			DL-CommonTransChInfo-r4				OPTIONAL,
		dl-DeletedTransChInfoList		DL-DeletedTransChInfoList-r7		OPTIONAL,
		dl-AddReconfTransChInfoList		DL-AddReconfTransChInfoList-r9		OPTIONAL,
	-- Physical channel IEs
		frequencyInfo					FrequencyInfo						OPTIONAL,
		multi-frequencyInfo				Multi-frequencyInfo-LCR-r7			OPTIONAL,
		dtx-drx-TimingInfo				DTX-DRX-TimingInfo-r7				OPTIONAL,
		dtx-drx-Info					DTX-DRX-Info-r7						OPTIONAL,
		hs-scch-LessInfo				HS-SCCH-LessInfo-r7					OPTIONAL,
		mimoParameters					MIMO-Parameters-r9					OPTIONAL,
		maxAllowedUL-TX-Power			MaxAllowedUL-TX-Power				OPTIONAL,
		ul-DPCH-Info					UL-DPCH-Info-r7						OPTIONAL,
		ul-EDCH-Information				UL-EDCH-Information-r9				OPTIONAL,
		ul-SecondaryCellInfoFDD			UL-SecondaryCellInfoFDD				OPTIONAL,
		ul-MulticarrierEDCHInfo-TDD128	UL-MulticarrierEDCHInfo-TDD128		OPTIONAL,
		dl-HSPDSCH-Information			DL-HSPDSCH-Information-r9			OPTIONAL,
		dl-CommonInformation			DL-CommonInformation-r10			OPTIONAL,
		dl-InformationPerRL-List		DL-InformationPerRL-List-r8			OPTIONAL,
		dl-SecondaryCellInfoFDD			DL-SecondaryCellInfoFDD-r10			OPTIONAL,
		additionalDLSecCellInfoListFDD	AdditionalDLSecCellInfoListFDD		OPTIONAL,
		controlChannelDRXInfo-TDD128	ControlChannelDRXInfo-TDD128-r8		OPTIONAL,
		sps-Information-TDD128			SPS-Information-TDD128-r8			OPTIONAL,
		mu-MIMO-Info-TDD128				MU-MIMO-Info-TDD128					OPTIONAL,
	-- MBMS IEs
		mbms-PL-ServiceRestrictInfo		MBMS-PL-ServiceRestrictInfo-r6		OPTIONAL,
	-- Measurement IEs for LCR
		cellDCHMeasOccasionInfo-TDD128	CellDCHMeasOccasionInfo-TDD128-r9	OPTIONAL
}

RadioBearerSetup-vb50ext-IEs ::= SEQUENCE {
		ulOLTDInfoFDD						UL-OLTD-InfoFDD			OPTIONAL
}

RadioBearerSetup-r11-IEs ::= SEQUENCE {
	-- User equipment IEs
		integrityProtectionModeInfo		IntegrityProtectionModeInfo-r7		OPTIONAL,
		cipheringModeInfo				CipheringModeInfo-r7				OPTIONAL,
		sr-vcc-Info						SR-VCC-Info							OPTIONAL,
		activationTime					ActivationTime						OPTIONAL,
		new-U-RNTI						U-RNTI								OPTIONAL,
		new-C-RNTI						C-RNTI								OPTIONAL,
		-- The IE "new-DSCH-RNTI" should not be included in FDD mode,
		-- and if received the UE behaviour is unspecified
		new-DSCH-RNTI					DSCH-RNTI							OPTIONAL,
		new-H-RNTI						H-RNTI								OPTIONAL,
		newPrimary-E-RNTI				E-RNTI								OPTIONAL,
		newSecondary-E-RNTI				E-RNTI								OPTIONAL,
		rrc-StateIndicator				RRC-StateIndicator,
		utran-DRX-CycleLengthCoeff		UTRAN-DRX-CycleLengthCoefficient-r7	OPTIONAL,
	-- UTRAN mobility IEs
		ura-Identity					URA-Identity						OPTIONAL,
		supportForChangeOfUE-Capability	BOOLEAN								OPTIONAL,
	-- Core network IEs
		cn-InformationInfo				CN-InformationInfo-r6				OPTIONAL,
	-- Radio bearer IEs
		srb-InformationSetupList		SRB-InformationSetupList-r11		OPTIONAL,
		rab-InformationSetupList		RAB-InformationSetupList-r11		OPTIONAL,
		rab-InformationReconfigList		RAB-InformationReconfigList-r8		OPTIONAL,
		rb-InformationReconfigList		RB-InformationReconfigList-r11		OPTIONAL,
		rb-InformationAffectedList		RB-InformationAffectedList-r8		OPTIONAL,
		dl-CounterSynchronisationInfo	DL-CounterSynchronisationInfo-r5	OPTIONAL,
		pdcp-ROHC-TargetMode			PDCP-ROHC-TargetMode				OPTIONAL,
	-- Transport channel IEs
		ul-CommonTransChInfo			UL-CommonTransChInfo-r4				OPTIONAL,
		ul-deletedTransChInfoList		UL-DeletedTransChInfoList-r6		OPTIONAL,
		ul-AddReconfTransChInfoList		UL-AddReconfTransChInfoList-r8		OPTIONAL,
		dl-CommonTransChInfo			DL-CommonTransChInfo-r4				OPTIONAL,
		dl-DeletedTransChInfoList		DL-DeletedTransChInfoList-r7		OPTIONAL,
		dl-AddReconfTransChInfoList		DL-AddReconfTransChInfoList-r11		OPTIONAL,
	-- Physical channel IEs
		frequencyInfo					FrequencyInfo						OPTIONAL,
		multi-frequencyInfo				Multi-frequencyInfo-LCR-r7			OPTIONAL,
		dtx-drx-TimingInfo				DTX-DRX-TimingInfo-r7				OPTIONAL,
		dtx-drx-Info					DTX-DRX-Info-r7						OPTIONAL,
		hs-scch-LessInfo				HS-SCCH-LessInfo-r7					OPTIONAL,
		mimoParameters					MIMO-Parameters-r9					OPTIONAL,
		mimo4x4Parameters				MIMO4x4-Parameters					OPTIONAL,
		maxAllowedUL-TX-Power			MaxAllowedUL-TX-Power				OPTIONAL,
		ul-DPCH-Info					UL-DPCH-Info-r11						OPTIONAL,
		ul-EDCH-Information				UL-EDCH-Information-r11				OPTIONAL,
		ul-SecondaryCellInfoFDD			UL-SecondaryCellInfoFDD				OPTIONAL,
		ul-MulticarrierEDCHInfo-TDD128	UL-MulticarrierEDCHInfo-TDD128		OPTIONAL,
		ul-CLTD-InfoFDD					UL-CLTD-InfoFDD						OPTIONAL,
		ul-OLTD-InfoFDD					UL-OLTD-InfoFDD						OPTIONAL,
		dl-HSPDSCH-Information			DL-HSPDSCH-Information-r11			OPTIONAL,
		dl-CommonInformation			DL-CommonInformation-r11			OPTIONAL,
		dl-InformationPerRL-List		DL-InformationPerRL-List-r11			OPTIONAL,
		dl-SecondaryCellInfoFDD			DL-SecondaryCellInfoFDD-r11			OPTIONAL,
		additionalDLSecCellInfoListFDD	AdditionalDLSecCellInfoListFDD-r11	OPTIONAL,
		additionalDLSecCellInfoListFDD2	AdditionalDLSecCellInfoListFDD2		OPTIONAL,
		commonERGCHInfoFDD				CommonERGCHInfoFDD					OPTIONAL,
		controlChannelDRXInfo-TDD128	ControlChannelDRXInfo-TDD128-r8		OPTIONAL,
		sps-Information-TDD128			SPS-Information-TDD128-r8			OPTIONAL,
		mu-MIMO-Info-TDD128				MU-MIMO-Info-TDD128					OPTIONAL,
	-- MBMS IEs
		mbms-PL-ServiceRestrictInfo		MBMS-PL-ServiceRestrictInfo-r6		OPTIONAL,
	-- Measurement IEs for LCR
		cellDCHMeasOccasionInfo-TDD128	CellDCHMeasOccasionInfo-TDD128-r9	OPTIONAL
}

-- ***************************************************
--
-- RADIO BEARER SETUP COMPLETE
--
-- ***************************************************

RadioBearerSetupComplete ::= SEQUENCE {
	-- User equipment IEs
		rrc-TransactionIdentifier		RRC-TransactionIdentifier,
		ul-IntegProtActivationInfo		IntegrityProtActivationInfo			OPTIONAL,
		-- TABULAR: UL-TimingAdvance is applicable for TDD mode only.
		ul-TimingAdvance				UL-TimingAdvance					OPTIONAL,
		start-Value				START-Value									OPTIONAL,
	-- Radio bearer IEs
		count-C-ActivationTime			ActivationTime						OPTIONAL,
		-- dummy is not used in this version of the specification and
		-- it should be ignored by the receiver.
		dummy							RB-ActivationTimeInfoList			OPTIONAL,
		ul-CounterSynchronisationInfo	UL-CounterSynchronisationInfo		OPTIONAL,
		laterNonCriticalExtensions		SEQUENCE {
			-- Container for additional R99 extensions
			radioBearerSetupComplete-r3-add-ext		BIT STRING		OPTIONAL,
			v770NonCriticalExtensions		SEQUENCE {
				radioBearerSetupComplete-v770ext
												RadioBearerSetupComplete-v770ext-IEs,
				nonCriticalExtensions			SEQUENCE {}		OPTIONAL
			}	OPTIONAL
		}	OPTIONAL
}

RadioBearerSetupComplete-v770ext-IEs ::= SEQUENCE {
		-- TABULAR: EXT-UL-TimingAdvance is applicable for TDD mode only.
		ext-UL-TimingAdvance					EXT-UL-TimingAdvance	OPTIONAL,
		deferredMeasurementControlReading		ENUMERATED { true }		OPTIONAL
}

-- ***************************************************
--
-- RADIO BEARER SETUP FAILURE
--
-- ***************************************************

RadioBearerSetupFailure ::= SEQUENCE {
	-- User equipment IEs
		rrc-TransactionIdentifier		RRC-TransactionIdentifier,
		failureCause					FailureCauseWithProtErr,
	-- Radio bearer IEs
		potentiallySuccesfulBearerList	RB-IdentityList						OPTIONAL,
		laterNonCriticalExtensions		SEQUENCE {
			-- Container for additional R99 extensions
			radioBearerSetupFailure-r3-add-ext		BIT STRING		OPTIONAL,
			nonCriticalExtensions			SEQUENCE {}		OPTIONAL
		}	OPTIONAL
}

-- ***************************************************
--
-- RRC CONNECTION REJECT
--
-- ***************************************************

RRCConnectionReject ::= CHOICE {
	r3								SEQUENCE {
		rrcConnectionReject-r3			RRCConnectionReject-r3-IEs,
		laterNonCriticalExtensions		SEQUENCE {
			-- Container for additional R99 extensions
			rrcConnectionReject-r3-add-ext		BIT STRING		OPTIONAL,
			v690NonCriticalExtensions			SEQUENCE {
				rrcConnectionReject-v690ext		RRCConnectionReject-v690ext-IEs,
				v6f0NonCriticalExtensions		SEQUENCE {
					rrcConnectionReject-v6f0ext		RRCConnectionReject-v6f0ext-IEs,
					v860NonCriticalExtensions		SEQUENCE {
						rrcConnectionReject-v860ext		RRCConnectionReject-v860ext-IEs,
						va40NonCriticalExtensions		SEQUENCE {
							rrcConnectionReject-va40ext		RRCConnectionReject-va40ext-IEs,
							vb50NonCriticalExtensions		SEQUENCE {
								rrcConnectionReject-vb50ext		RRCConnectionReject-vb50ext-IEs,
								nonCriticalExtensions			SEQUENCE {}		OPTIONAL
							}	OPTIONAL
						}	OPTIONAL
					}	OPTIONAL
				}	OPTIONAL
			}	OPTIONAL
		}	OPTIONAL
	},
	later-than-r3					SEQUENCE {
		initialUE-Identity				InitialUE-Identity,
		rrc-TransactionIdentifier		RRC-TransactionIdentifier,
		criticalExtensions				SEQUENCE {}
	}
}

RRCConnectionReject-r3-IEs ::= SEQUENCE {
	-- TABULAR: Integrity protection shall not be performed on this message.
	-- User equipment IEs
		initialUE-Identity				InitialUE-Identity,
		rrc-TransactionIdentifier		RRC-TransactionIdentifier,
		rejectionCause					RejectionCause,
		waitTime						WaitTime,
		redirectionInfo					RedirectionInfo					OPTIONAL
}

RRCConnectionReject-v690ext-IEs ::= SEQUENCE {
	redirectionInfo-v690ext				GSM-TargetCellInfoList			OPTIONAL
}

RRCConnectionReject-v6f0ext-IEs ::= SEQUENCE {
	countingCompletion					ENUMERATED { true }				OPTIONAL
}

RRCConnectionReject-v860ext-IEs ::= SEQUENCE {
	redirectionInfo					RedirectionInfo-v860ext				OPTIONAL
}

RRCConnectionReject-va40ext-IEs ::= SEQUENCE {
	extendedWaitTime 				ExtendedWaitTime					OPTIONAL
}

RRCConnectionReject-vb50ext-IEs ::= SEQUENCE {
	eutra-TargetFreqInfoList	EUTRA-TargetFreqInfoList-vb50ext		OPTIONAL
}

-- ***************************************************
--
-- RRC CONNECTION RELEASE
--
-- ***************************************************

RRCConnectionRelease ::= CHOICE {
	r3								SEQUENCE {
		rrcConnectionRelease-r3			RRCConnectionRelease-r3-IEs,
		laterNonCriticalExtensions		SEQUENCE {
			-- Container for additional R99 extensions
			rrcConnectionRelease-r3-add-ext		BIT STRING		OPTIONAL,
			v690NonCriticalExtensions			SEQUENCE { 
				rrcConnectionRelease-v690ext		RRCConnectionRelease-v690ext-IEs,
				v770NonCriticalExtensions			SEQUENCE {
					rrcConnectionRelease-v770ext		RRCConnectionRelease-v770ext-IEs,
					v860NonCriticalExtensions			SEQUENCE {
						rrcConnectionRelease-v860ext		RRCConnectionRelease-v860ext-IEs,
						va40NonCriticalExtensions			SEQUENCE {
							rrcConnectionRelease-va40ext		RRCConnectionRelease-va40ext-IEs,
							nonCriticalExtensions				SEQUENCE {}		OPTIONAL
						}	OPTIONAL
					}	OPTIONAL
				}	OPTIONAL
			}	OPTIONAL
		}	OPTIONAL
	},
	later-than-r3					SEQUENCE {
		rrc-TransactionIdentifier		RRC-TransactionIdentifier,
		criticalExtensions				CHOICE {
			r4								SEQUENCE {
				rrcConnectionRelease-r4			RRCConnectionRelease-r4-IEs,
				v4d0NonCriticalExtensions			SEQUENCE {
					-- Container for adding non critical extensions after freezing REL-6
					rrcConnectionRelease-r4-add-ext		BIT STRING		OPTIONAL,
					v690NonCriticalExtensions			SEQUENCE {
						rrcConnectionRelease-v690ext		RRCConnectionRelease-v690ext-IEs,
						v770NonCriticalExtensions			SEQUENCE {
							rrcConnectionRelease-v770ext		RRCConnectionRelease-v770ext-IEs,
							v860NonCriticalExtensions			SEQUENCE {
								rrcConnectionRelease-v860ext	RRCConnectionRelease-v860ext-IEs,
								va40NonCriticalExtensions			SEQUENCE {
									rrcConnectionRelease-va40ext		
																RRCConnectionRelease-va40ext-IEs,
									vb50NonCriticalExtensions			SEQUENCE {
										rrcConnectionRelease-vb50ext		
																RRCConnectionRelease-vb50ext-IEs,
										nonCriticalExtensions			SEQUENCE {}		OPTIONAL
									}	OPTIONAL
								}	OPTIONAL
							}	OPTIONAL
						}	OPTIONAL
					}	OPTIONAL
				}	OPTIONAL
			},
			criticalExtensions				SEQUENCE {}
		}
	}
}

RRCConnectionRelease-r3-IEs ::= SEQUENCE {
	-- User equipment IEs
		rrc-TransactionIdentifier		RRC-TransactionIdentifier,
		-- n-308 is conditional on the UE state
		n-308							N-308								OPTIONAL,
		releaseCause					ReleaseCause,
		rplmn-information				Rplmn-Information					OPTIONAL
}

RRCConnectionRelease-r4-IEs ::= SEQUENCE {
	-- User equipment IEs
		-- n-308 is conditional on the UE state.
		n-308							N-308								OPTIONAL,
		releaseCause					ReleaseCause,
		rplmn-information				Rplmn-Information-r4				OPTIONAL
}

RRCConnectionRelease-v690ext-IEs ::= SEQUENCE {
		redirectionInfo-v690ext			RedirectionInfo-r6					OPTIONAL
}

RRCConnectionRelease-v770ext-IEs ::= SEQUENCE {
	-- User equipment IEs
		ueMobilityStateIndicator		High-MobilityDetected				OPTIONAL
}

RRCConnectionRelease-v860ext-IEs ::= SEQUENCE {
	-- Other IEs
		redirectionInfo					RedirectionInfo-v860ext				OPTIONAL
}

RRCConnectionRelease-va40ext-IEs ::= SEQUENCE {
	extendedWaitTime 				ExtendedWaitTime					OPTIONAL
}

RRCConnectionRelease-vb50ext-IEs ::= SEQUENCE {
	-- Other IEs
		eutra-TargetFreqInfoList	EUTRA-TargetFreqInfoList-vb50ext	OPTIONAL
}

-- ***************************************************
--
-- RRC CONNECTION RELEASE for CCCH
--
-- ***************************************************

RRCConnectionRelease-CCCH ::= CHOICE {
	r3								SEQUENCE {
		rrcConnectionRelease-CCCH-r3	RRCConnectionRelease-CCCH-r3-IEs,
		laterNonCriticalExtensions		SEQUENCE {
			-- Container for additional R99 extensions
			rrcConnectionRelease-CCCH-r3-add-ext		BIT STRING		OPTIONAL,
			v690NonCriticalExtensions		SEQUENCE { 
				rrcConnectionRelease-v690ext	RRCConnectionRelease-CCCH-v690ext-IEs,
				v860NonCriticalExtensions		SEQUENCE {
					rrcConnectionRelease-v860ext	RRCConnectionRelease-CCCH-v860ext-IEs,
					va40NonCriticalExtensions			SEQUENCE {
						rrcConnectionRelease-va40ext		RRCConnectionRelease-va40ext-IEs,
						nonCriticalExtensions				SEQUENCE {}	OPTIONAL
					}	OPTIONAL
				}	OPTIONAL
			}	OPTIONAL
		}	OPTIONAL
	},
	later-than-r3					SEQUENCE {
		u-RNTI							U-RNTI,
		rrc-TransactionIdentifier		RRC-TransactionIdentifier,
		criticalExtensions				CHOICE {
			r4								SEQUENCE {
				rrcConnectionRelease-CCCH-r4	RRCConnectionRelease-CCCH-r4-IEs,
				v4d0NonCriticalExtensions			SEQUENCE {
					-- Container for adding non critical extensions after freezing REL-5
					rrcConnectionRelease-CCCH-r4-add-ext		BIT STRING		OPTIONAL,
					v690NonCriticalExtensions		SEQUENCE { 
						rrcConnectionRelease-v690ext	RRCConnectionRelease-CCCH-v690ext-IEs,
						v860NonCriticalExtensions		SEQUENCE {
							rrcConnectionRelease-v860ext	RRCConnectionRelease-CCCH-v860ext-IEs,
							va40NonCriticalExtensions			SEQUENCE {
								rrcConnectionRelease-va40ext		
																RRCConnectionRelease-va40ext-IEs,
								nonCriticalExtensions			SEQUENCE {}		OPTIONAL
							}	OPTIONAL
						}	OPTIONAL
					}	OPTIONAL
				}	OPTIONAL
			},
			criticalExtensions				SEQUENCE {
				-- TABULAR: CHOICE IdentityType (U-RNTI, GroupIdentity) is replaced with the 
				-- optional element groupIdentity, since the U-RNTI is mandatory in ASN.1.
				-- In case CHOICE IdentityType is equal to GroupIdentity the value of the U-RNTI 
				-- shall be ignored by a UE complying with this version of the message.
				groupIdentity		SEQUENCE ( SIZE (1 .. maxURNTI-Group) ) OF
											GroupReleaseInformation		OPTIONAL,
				criticalExtensions				CHOICE {
					r5								SEQUENCE {
						rrcConnectionRelease-CCCH-r5	RRCConnectionRelease-CCCH-r5-IEs,
						-- Container for adding non critical extensions after freezing REL-6
						rrcConnectionRelease-CCCH-r5-add-ext		BIT STRING		OPTIONAL,
						v690NonCriticalExtensions		SEQUENCE { 
							rrcConnectionRelease-v690ext	RRCConnectionRelease-CCCH-v690ext-IEs,
							v860NonCriticalExtensions		SEQUENCE {
								rrcConnectionRelease-v860ext
															RRCConnectionRelease-CCCH-v860ext-IEs,
								va40NonCriticalExtensions			SEQUENCE {
									rrcConnectionRelease-va40ext		
																RRCConnectionRelease-va40ext-IEs,
									nonCriticalExtensions		SEQUENCE {}	OPTIONAL
								}	OPTIONAL
							}	OPTIONAL
						}	OPTIONAL
					},
					criticalExtensions				SEQUENCE {}
				}
			}
		}
	}
}

RRCConnectionRelease-CCCH-r3-IEs ::= SEQUENCE {
	-- User equipment IEs
		u-RNTI							U-RNTI,
	-- The rest of the message is identical to the one sent on DCCH.
		rrcConnectionRelease			RRCConnectionRelease-r3-IEs
}

RRCConnectionRelease-CCCH-r4-IEs ::= SEQUENCE {
	-- The rest of the message is identical to the one sent on DCCH.
		rrcConnectionRelease			RRCConnectionRelease-r4-IEs
}

-- The R5 and R4 sequence of IEs are identical in this message
RRCConnectionRelease-CCCH-r5-IEs ::= RRCConnectionRelease-CCCH-r4-IEs

-- The R6 non-critical extension is identical to the one sent on DCCH.
RRCConnectionRelease-CCCH-v690ext-IEs ::= RRCConnectionRelease-v690ext-IEs

-- The R8 non-critical extension is identical to the one sent on DCCH.
RRCConnectionRelease-CCCH-v860ext-IEs ::= RRCConnectionRelease-v860ext-IEs

-- The R10 non-critical extension is identical to the one sent on DCCH.
RRCConnectionRelease-CCCH-va40ext-IEs ::= RRCConnectionRelease-va40ext-IEs

-- ***************************************************
--
-- RRC CONNECTION RELEASE COMPLETE
--
-- ***************************************************

RRCConnectionReleaseComplete ::= SEQUENCE {
	-- User equipment IEs
		rrc-TransactionIdentifier		RRC-TransactionIdentifier,
		errorIndication					FailureCauseWithProtErr				OPTIONAL,
		laterNonCriticalExtensions		SEQUENCE {
			-- Container for additional R99 extensions
			rrcConnectionReleaseComplete-r3-add-ext		BIT STRING		OPTIONAL,
			nonCriticalExtensions			SEQUENCE {}		OPTIONAL
		}	OPTIONAL
}

-- ***************************************************
--
-- RRC CONNECTION REQUEST
--
-- ***************************************************

RRCConnectionRequest ::= SEQUENCE {
	-- TABULAR: Integrity protection shall not be performed on this message.
	-- User equipment IEs
		initialUE-Identity				InitialUE-Identity,
		establishmentCause				EstablishmentCause,
		-- protocolErrorIndicator is MD, but for compactness reasons no default value
		-- has been assigned to it.
		protocolErrorIndicator			ProtocolErrorIndicator,
	-- Measurement IEs
		measuredResultsOnRACH			MeasuredResultsOnRACH				OPTIONAL,
	--	Non critical Extensions
		v3d0NonCriticalExtensions			SEQUENCE {
			rRCConnectionRequest-v3d0ext 	RRCConnectionRequest-v3d0ext-IEs,
		-- Reserved for future non critical extension
			v4b0NonCriticalExtensions			SEQUENCE {
				rrcConnectionRequest-v4b0ext		RRCConnectionRequest-v4b0ext-IEs,
				v590NonCriticalExtensions			SEQUENCE {
					rrcConnectionRequest-v590ext		RRCConnectionRequest-v590ext-IEs,
					v690NonCriticalExtensions			SEQUENCE {
						rrcConnectionRequest-v690ext	RRCConnectionRequest-v690ext-IEs,
						-- Reserved for future non critical extension
						v6b0NonCriticalExtensions		SEQUENCE {
							rrcConnectionRequest-v6b0ext	RRCConnectionRequest-v6b0ext-IEs,
							v6e0NonCriticalExtensions		SEQUENCE {
								rrcConnectionRequest-v6e0ext	RRCConnectionRequest-v6e0ext-IEs,
								v770NonCriticalExtensions		SEQUENCE {
									rrcConnectionRequest-v770ext
																RRCConnectionRequest-v770ext-IEs,
									v7b0NonCriticalExtensions		SEQUENCE {
										rrcConnectionRequest-v7b0ext
																RRCConnectionRequest-v7b0ext-IEs,
										v860NonCriticalExtensions		SEQUENCE {
											rrcConnectionRequest-v860ext
																RRCConnectionRequest-v860ext-IEs,
											v7e0NonCriticalExtensions		SEQUENCE {
												rrcConnectionRequest-v7e0ext
																RRCConnectionRequest-v7e0ext-IEs,
												v7g0NonCriticalExtensions		SEQUENCE {
													rrcConnectionRequest-v7g0ext
																RRCConnectionRequest-v7g0ext-IEs,
													v920NonCriticalExtensions		SEQUENCE {
														rrcConnectionRequest-v920ext
																RRCConnectionRequest-v920ext-IEs,
														v940NonCriticalExtensions	SEQUENCE {
															rrcConnectionRequest-v940ext
																RRCConnectionRequest-v940ext-IEs,
															va40NonCriticalExtensions
																RRCConnectionRequest-NonCriticalExts-va40-IEs		
																								OPTIONAL
															}	OPTIONAL
													}	OPTIONAL
												}	OPTIONAL
											}	OPTIONAL
										}	OPTIONAL
									}	OPTIONAL
								}	OPTIONAL
							}	OPTIONAL
						}	OPTIONAL
					}	OPTIONAL
				}	OPTIONAL
			}	OPTIONAL
		} 	OPTIONAL
}

RRCConnectionRequest-v3d0ext-IEs ::= SEQUENCE {
	-- User equipment IEs
		uESpecificBehaviourInformation1idle		UESpecificBehaviourInformation1idle		OPTIONAL
}

RRCConnectionRequest-v4b0ext-IEs ::= 	SEQUENCE {
	-- User equipment IEs
		accessStratumReleaseIndicator			AccessStratumReleaseIndicator
}

RRCConnectionRequest-v590ext-IEs ::= 	SEQUENCE {
	-- User equipment IEs
		predefinedConfigStatusInfo			BOOLEAN
}

RRCConnectionRequest-v690ext-IEs ::=	SEQUENCE {
	-- User equipment IEs
		ueCapabilityIndication				ENUMERATED { hsdch, hsdch-edch }	OPTIONAL,
	-- Measurement IEs
		measuredResultsOnRACHinterFreq		MeasuredResultsOnRACHinterFreq			OPTIONAL,
		domainIndicator 					CHOICE {
			cs-domain							SEQUENCE {
				csCallType							ENUMERATED {speech, video, other, spare }
			},
			ps-domain 							NULL
		}
}

RRCConnectionRequest-v6b0ext-IEs ::=	SEQUENCE {
	-- MBMS IEs
		mbmsSelectedServices				MBMS-SelectedServicesShort			OPTIONAL
}

RRCConnectionRequest-v6e0ext-IEs ::= 	SEQUENCE {
	-- User equipment IEs
		supportForFDPCH						ENUMERATED { true }			OPTIONAL
}

RRCConnectionRequest-v770ext-IEs ::=	SEQUENCE {
	-- User equipment IEs
		ueMobilityStateIndicator			High-MobilityDetected				OPTIONAL,
		hspdschReception-CellFach			ENUMERATED { true }					OPTIONAL,
		mac-ehsSupport						ENUMERATED { true }					OPTIONAL,
		discontinuousDpcchTransmission		ENUMERATED { true }					OPTIONAL
}

RRCConnectionRequest-v7b0ext-IEs ::=	SEQUENCE {
	-- User equipment IEs
		supportForE-FDPCH					ENUMERATED { true }					OPTIONAL
}

RRCConnectionRequest-v7e0ext-IEs ::=	SEQUENCE {
		supportForCSVoiceoverHSPA			ENUMERATED { true }					OPTIONAL
}

RRCConnectionRequest-v7g0ext-IEs ::=	SEQUENCE {
	-- Measurement IEs
		measuredResultsOnRACH-v7g0ext		MeasuredResultsOnRACH-v7g0ext		OPTIONAL
}

RRCConnectionRequest-v860ext-IEs ::= 	SEQUENCE {
	-- User equipment IEs
		supportOfCommonEDCH					ENUMERATED { true }					OPTIONAL,
		multiCellSupport					ENUMERATED { true }					OPTIONAL,
		pre-redirectionInfo					Pre-RedirectionInfo					OPTIONAL,
		supportOfMACiis						ENUMERATED { true }					OPTIONAL,
		supportOfSPSOperation				ENUMERATED { true }					OPTIONAL
}

RRCConnectionRequest-v920ext-IEs ::=	SEQUENCE {
	-- User equipment IEs
		supportOfDualCellMIMO				ENUMERATED { true }					OPTIONAL
}

RRCConnectionRequest-v940ext-IEs ::=	SEQUENCE {
	-- User equipment IEs
		systemInformationContainerStoredIndicator	ENUMERATED { true }			OPTIONAL
}

RRCConnectionRequest-v9b0ext-IEs ::=	SEQUENCE {
	-- User equipment IEs
		cSFBIndication						ENUMERATED { true }					OPTIONAL
}

RRCConnectionRequest-NonCriticalExts-va40-IEs ::=	SEQUENCE {
	rrcConnectionRequest-va40ext		RRCConnectionRequest-va40ext-IEs,
	v9b0NonCriticalExtensions			SEQUENCE	{
		rrcConnectionRequest-v9b0ext		RRCConnectionRequest-v9b0ext-IEs,
		vb50NonCriticalExtensions		SEQUENCE {
			rrcConnectionRequest-vb50ext						RRCConnectionRequest-vb50ext-IEs,
			nonCriticalExtensions				SEQUENCE {} OPTIONAL
		}	OPTIONAL
	}	OPTIONAL
}

RRCConnectionRequest-va40ext-IEs ::=	SEQUENCE {
	-- User equipment IEs
		-- For 1.28 Mcps TDD, IE ”supportOfMoreThanTwoCellsOrMIMO4x4” represent MU-MIMO capability,
		-- higherRate indicates uplink and downlink MU-MIMO, lowerRate indicates uplink MU-MIMO
		supportOfMoreThanTwoCellsOrMIMO4x4	ENUMERATED { higherRate, lowerRate }		OPTIONAL,
		supportOf1stFrequencyBand			ENUMERATED { true }							OPTIONAL,
		supportOf2ndFrequencyBand			ENUMERATED { true }							OPTIONAL
}

RRCConnectionRequest-vb50ext-IEs ::=	SEQUENCE {
	-- Measurement IEs
	measuredResultsOnRACHEUTRAFreq		MeasuredResultsOnRACH-EUTRAFreq		OPTIONAL
}

-- ***************************************************
--
-- RRC CONNECTION SETUP
--
-- ***************************************************

RRCConnectionSetup ::= CHOICE {
	r3								SEQUENCE {
		rrcConnectionSetup-r3			RRCConnectionSetup-r3-IEs,
		laterNonCriticalExtensions		SEQUENCE {
			-- Container for additional R99 extensions
			rrcConnectionSetup-r3-add-ext	BIT STRING		OPTIONAL,
			v4b0NonCriticalExtensions		SEQUENCE { 
				rrcConnectionSetup-v4b0ext		RRCConnectionSetup-v4b0ext-IEs,
				v590NonCriticalExtensions		SEQUENCE { 
					rrcConnectionSetup-v590ext		RRCConnectionSetup-v590ext-IEs,
					v690NonCriticalExtensions		SEQUENCE {
						rrcConnectionSetup-v690ext		RRCConnectionSetup-v690ext-IEs,
						nonCriticalExtensions			SEQUENCE {}		OPTIONAL
					}	OPTIONAL
				}	OPTIONAL
			}	OPTIONAL
		}	OPTIONAL
	},
	later-than-r3					SEQUENCE {
		initialUE-Identity				InitialUE-Identity,
		rrc-TransactionIdentifier		RRC-TransactionIdentifier,
		criticalExtensions				CHOICE {
			r4								SEQUENCE {
				rrcConnectionSetup-r4			RRCConnectionSetup-r4-IEs,
				v4d0NonCriticalExtensions			SEQUENCE {
					-- Container for adding non critical extensions after freezing REL-5
					rrcConnectionSetup-r4-add-ext	BIT STRING		OPTIONAL,
					v590NonCriticalExtensions		SEQUENCE { 
						rrcConnectionSetup-v590ext		RRCConnectionSetup-v590ext-IEs,
						v690NonCriticalExtensions		SEQUENCE {
							rrcConnectionSetup-v690ext		RRCConnectionSetup-v690ext-IEs,
							nonCriticalExtensions			SEQUENCE {}		OPTIONAL
						}	OPTIONAL
					}	OPTIONAL
				}	OPTIONAL
			},
			criticalExtensions					CHOICE {
				r5								SEQUENCE {
					rrcConnectionSetup-r5			RRCConnectionSetup-r5-IEs,
					-- Container for adding non critical extensions after freezing REL-6
					rrcConnectionSetup-r5-add-ext	BIT STRING		OPTIONAL,
					v690NonCriticalExtensions		SEQUENCE {
						rrcConnectionSetup-v690ext		RRCConnectionSetup-v690ext-IEs,
						nonCriticalExtensions			SEQUENCE {}		OPTIONAL
					}	OPTIONAL
				},
				criticalExtensions				CHOICE {
					r6								SEQUENCE {
						rrcConnectionSetup-r6			RRCConnectionSetup-r6-IEs,
						-- Container for adding non critical extensions after freezing REL-7
						rrcConnectionSetup-r6-add-ext	BIT STRING					OPTIONAL,
						v6b0NonCriticalExtensions		SEQUENCE {
							rrcConnectionSetup-v6b0ext		RRCConnectionSetup-v6b0ext-IEs,
							nonCriticalExtensions			SEQUENCE {}				OPTIONAL
						}	OPTIONAL
					},
					criticalExtensions				CHOICE {
						r7								SEQUENCE {
							rrcConnectionSetup-r7			RRCConnectionSetup-r7-IEs,
							-- Container for adding non critical extensions after freezing REL-8
							rrcConnectionSetup-r7-add-ext	BIT STRING					OPTIONAL,
							v780NonCriticalExtensions		SEQUENCE {
								rrcConnectionSetup-v780ext		RRCConnectionSetup-v780ext-IEs,
								v7d0NonCriticalExtensions		SEQUENCE {
									rrcConnectionSetup-v7d0ext		RRCConnectionSetup-v7d0ext-IEs,
									nonCriticalExtensions			SEQUENCE {}		OPTIONAL
								}	OPTIONAL
							}	OPTIONAL
						},
						criticalExtensions				CHOICE {
							r8								SEQUENCE {
								rrcConnectionSetup-r8			RRCConnectionSetup-r8-IEs,
								-- Container for adding non critical extensions after freezing REL-9
								rrcConnectionSetup-r8-add-ext	BIT STRING				OPTIONAL,
								v7d0NonCriticalExtensions		SEQUENCE {
									rrcConnectionSetup-v7d0ext		RRCConnectionSetup-v7d0ext-IEs,
									v890NonCriticalExtensions		SEQUENCE {
										rrcConnectionSetup-v890ext
																	RRCConnectionSetup-v890ext-IEs,
										v8a0NonCriticalExtensions		SEQUENCE {
											rrcConnectionSetup-v8a0ext
																	RRCConnectionSetup-v8a0ext-IEs,
											nonCriticalExtensions			SEQUENCE {}		OPTIONAL
										}	OPTIONAL
									}	OPTIONAL
								}	OPTIONAL
							},
							criticalExtensions				CHOICE {
								r9								SEQUENCE {
									rrcConnectionSetup-r9			RRCConnectionSetup-r9-IEs,
									-- Container for adding non critical extensions after 
									-- freezing REL-10
									rrcConnectionSetup-r9-add-ext
																	BIT STRING		OPTIONAL,
									v950NonCriticalExtensions		SEQUENCE {
										rrcConnectionSetup-v950ext	RRCConnectionSetup-v950ext-IEs,
										nonCriticalExtensions			SEQUENCE {}		OPTIONAL
									}	OPTIONAL
								},
								criticalExtensions				CHOICE {
									r10								SEQUENCE {
										rrcConnectionSetup-r10			RRCConnectionSetup-r10-IEs,
										-- Container for adding non critical extensions after 
										-- freezing REL-11
										rrcConnectionSetup-r10-add-ext
																			BIT STRING	OPTIONAL,
										nonCriticalExtensions			SEQUENCE {}		OPTIONAL
									},
									criticalExtensions				CHOICE {
										r11								SEQUENCE {
											rrcConnectionSetup-r11			
																		RRCConnectionSetup-r11-IEs,
											-- Container for adding non critical extensions after 
											-- freezing REL-12
											rrcConnectionSetup-r11-add-ext
																			BIT STRING	OPTIONAL,
											nonCriticalExtensions			SEQUENCE {}		OPTIONAL
										},
										criticalExtensions				SEQUENCE {}
									}
								}
							}
						}
					}
				}
			}
		}
	}
}

RRCConnectionSetup-r3-IEs ::= SEQUENCE {
	-- TABULAR: Integrity protection shall not be performed on this message.
	-- User equipment IEs
		initialUE-Identity				InitialUE-Identity,
		rrc-TransactionIdentifier		RRC-TransactionIdentifier,
		activationTime					ActivationTime						OPTIONAL,
		new-U-RNTI						U-RNTI,
		new-c-RNTI						C-RNTI								OPTIONAL,
		rrc-StateIndicator				RRC-StateIndicator,
		utran-DRX-CycleLengthCoeff		UTRAN-DRX-CycleLengthCoefficient,
		-- TABULAR: If capabilityUpdateRequirement is not present, the default value
		-- defined in 10.3.3.2 shall be used.
		capabilityUpdateRequirement		CapabilityUpdateRequirement			OPTIONAL,
	-- Radio bearer IEs
		srb-InformationSetupList		SRB-InformationSetupList2,
	-- Transport channel IEs
		ul-CommonTransChInfo			UL-CommonTransChInfo				OPTIONAL,
		-- NOTE: ul-AddReconfTransChInfoList should be optional in later versions of
		-- this message
		ul-AddReconfTransChInfoList		UL-AddReconfTransChInfoList,
		dl-CommonTransChInfo			DL-CommonTransChInfo				OPTIONAL,
		-- NOTE: dl-AddReconfTransChInfoList should be optional in later versions
		-- of this message
		dl-AddReconfTransChInfoList		DL-AddReconfTransChInfoList,
	-- Physical channel IEs
		frequencyInfo					FrequencyInfo						OPTIONAL,
		maxAllowedUL-TX-Power			MaxAllowedUL-TX-Power				OPTIONAL,
		ul-ChannelRequirement			UL-ChannelRequirement				OPTIONAL,
		dl-CommonInformation			DL-CommonInformation				OPTIONAL,
		dl-InformationPerRL-List		DL-InformationPerRL-List			OPTIONAL
}

RRCConnectionSetup-v4b0ext-IEs ::= SEQUENCE {
		capabilityUpdateRequirement-r4-ext	CapabilityUpdateRequirement-r4-ext	OPTIONAL,
	-- Physical channel IEs
		-- dummy is not used in this version of the specification, it should
		-- not be sent and if received it should be ignored.
		dummy								SSDT-UL								OPTIONAL,
		-- The order of the RLs in IE cell-id-PerRL-List is the same as
		-- in IE DL-InformationPerRL-List included in this message
		cell-id-PerRL-List					CellIdentity-PerRL-List				OPTIONAL
}

RRCConnectionSetup-v590ext-IEs ::= SEQUENCE {
	-- User equipment IEs
		systemSpecificCapUpdateReq		SystemSpecificCapUpdateReq-v590ext		OPTIONAL,
	-- Physical channel IEs
		dl-TPC-PowerOffsetPerRL-List	DL-TPC-PowerOffsetPerRL-List		OPTIONAL
}

RRCConnectionSetup-r4-IEs ::= SEQUENCE {
	-- TABULAR: Integrity protection shall not be performed on this message.
		activationTime					ActivationTime						OPTIONAL,
		new-U-RNTI						U-RNTI,
		new-c-RNTI						C-RNTI								OPTIONAL,
		rrc-StateIndicator				RRC-StateIndicator,
		utran-DRX-CycleLengthCoeff		UTRAN-DRX-CycleLengthCoefficient,
		-- TABULAR: If capabilityUpdateRequirement is not present, the default value
		-- defined in 10.3.3.2 shall be used.
		capabilityUpdateRequirement		CapabilityUpdateRequirement-r4		OPTIONAL,
	-- Radio bearer IEs
		srb-InformationSetupList		SRB-InformationSetupList2,
	-- Transport channel IEs
		ul-CommonTransChInfo			UL-CommonTransChInfo-r4				OPTIONAL,
		ul-AddReconfTransChInfoList		UL-AddReconfTransChInfoList			OPTIONAL,
		dl-CommonTransChInfo			DL-CommonTransChInfo-r4				OPTIONAL,
		dl-AddReconfTransChInfoList		DL-AddReconfTransChInfoList-r4		OPTIONAL,
	-- Physical channel IEs
		frequencyInfo					FrequencyInfo						OPTIONAL,
		maxAllowedUL-TX-Power			MaxAllowedUL-TX-Power				OPTIONAL,
		ul-ChannelRequirement			UL-ChannelRequirement-r4			OPTIONAL,
		dl-CommonInformation			DL-CommonInformation-r4				OPTIONAL,
		dl-InformationPerRL-List		DL-InformationPerRL-List-r4			OPTIONAL
}

RRCConnectionSetup-r5-IEs ::= SEQUENCE {
	-- TABULAR: Integrity protection shall not be performed on this message.
		activationTime					ActivationTime						OPTIONAL,
		new-U-RNTI						U-RNTI,
		new-c-RNTI						C-RNTI								OPTIONAL,
		rrc-StateIndicator				RRC-StateIndicator,
		utran-DRX-CycleLengthCoeff		UTRAN-DRX-CycleLengthCoefficient,
		-- TABULAR: If capabilityUpdateRequirement is not present, the default value
		-- defined in 10.3.3.2 shall be used.
		capabilityUpdateRequirement		CapabilityUpdateRequirement-r5		OPTIONAL,
	-- Specification mode information
		specificationMode				CHOICE {
			complete						SEQUENCE {
				-- Radio bearer IEs
				srb-InformationSetupList		SRB-InformationSetupList2,
				-- Transport channel IEs
				ul-CommonTransChInfo			UL-CommonTransChInfo-r4				OPTIONAL,
				ul-AddReconfTransChInfoList		UL-AddReconfTransChInfoList			OPTIONAL,
				dl-CommonTransChInfo			DL-CommonTransChInfo-r4				OPTIONAL,
				dl-AddReconfTransChInfoList		DL-AddReconfTransChInfoList-r4		OPTIONAL
			},
			preconfiguration				SEQUENCE {
				-- All IEs that include an FDD/TDD choice are split in two IEs for this message,
				-- one for the FDD only elements and one for the TDD only elements, so that one
				-- FDD/TDD choice in this level is sufficient.
				preConfigMode					CHOICE {
					predefinedConfigIdentity		PredefinedConfigIdentity,
					defaultConfig					SEQUENCE {
						defaultConfigMode				DefaultConfigMode,
						defaultConfigIdentity 			DefaultConfigIdentity-r5
					}
				}
			}
		},
	-- Physical channel IEs
		frequencyInfo					FrequencyInfo						OPTIONAL,
		maxAllowedUL-TX-Power			MaxAllowedUL-TX-Power				OPTIONAL,
		ul-ChannelRequirement			UL-ChannelRequirement-r4			OPTIONAL,
		dl-CommonInformation			DL-CommonInformation-r4				OPTIONAL,
		dl-InformationPerRL-List		DL-InformationPerRL-List-r5bis		OPTIONAL
}

RRCConnectionSetup-v690ext-IEs ::= SEQUENCE {
	-- Physical Channel IEs
		beaconPLEst						BEACON-PL-Est						OPTIONAL,
		postVerificationPeriod			ENUMERATED { true }					OPTIONAL
}

RRCConnectionSetup-r6-IEs ::= SEQUENCE {
	-- TABULAR: Integrity protection shall not be performed on this message.
		activationTime					ActivationTime						OPTIONAL,
		new-U-RNTI						U-RNTI,
		new-c-RNTI						C-RNTI								OPTIONAL,
		new-H-RNTI						H-RNTI								OPTIONAL,
		newPrimary-E-RNTI				E-RNTI								OPTIONAL,
		newSecondary-E-RNTI				E-RNTI								OPTIONAL,
		rrc-StateIndicator				RRC-StateIndicator,
		utran-DRX-CycleLengthCoeff		UTRAN-DRX-CycleLengthCoefficient,
		-- TABULAR: If capabilityUpdateRequirement is not present, the default value
		-- defined in 10.3.3.2 shall be used.
		capabilityUpdateRequirement		CapabilityUpdateRequirement-r5		OPTIONAL,
	-- Specification mode information
		specificationMode				CHOICE {
			complete						SEQUENCE {
				-- Radio bearer IEs
				srb-InformationSetupList		SRB-InformationSetupList2-r6,
				-- Transport channel IEs
				ul-CommonTransChInfo			UL-CommonTransChInfo-r4				OPTIONAL,
				ul-AddReconfTransChInfoList		UL-AddReconfTransChInfoList-r6		OPTIONAL,
				dl-CommonTransChInfo			DL-CommonTransChInfo-r4				OPTIONAL,
				dl-AddReconfTransChInfoList		DL-AddReconfTransChInfoList-r5		OPTIONAL
			},
			preconfiguration				SEQUENCE {
				-- All IEs that include an FDD/TDD choice are split in two IEs for this message,
				-- one for the FDD only elements and one for the TDD only elements, so that one
				-- FDD/TDD choice in this level is sufficient.
				preConfigMode					CHOICE {
					predefinedConfigIdentity		PredefinedConfigIdentity,
					defaultConfig					SEQUENCE {
						defaultConfigMode				DefaultConfigMode,
						defaultConfigIdentity 			DefaultConfigIdentity-r6
					}
				}
			}
		},
	-- Physical channel IEs
		frequencyInfo					FrequencyInfo						OPTIONAL,
		maxAllowedUL-TX-Power			MaxAllowedUL-TX-Power				OPTIONAL,
		ul-DPCH-Info					UL-DPCH-Info-r6						OPTIONAL,
		ul-EDCH-Information				UL-EDCH-Information-r6				OPTIONAL,
		dl-HSPDSCH-Information			DL-HSPDSCH-Information-r6			OPTIONAL,
		dl-CommonInformation			DL-CommonInformation-r6				OPTIONAL,
		dl-InformationPerRL-List		DL-InformationPerRL-List-r6			OPTIONAL
}

RRCConnectionSetup-v6b0ext-IEs ::= SEQUENCE {
	-- Physical channel IEs
		dl-InformationPerRL-List-v6b0ext	DL-InformationPerRL-List-v6b0ext	OPTIONAL
}

RRCConnectionSetup-r7-IEs ::= SEQUENCE {
	-- TABULAR: Integrity protection shall not be performed on this message.
		activationTime					ActivationTime						OPTIONAL,
		new-U-RNTI						U-RNTI,
		new-c-RNTI						C-RNTI								OPTIONAL,
		new-H-RNTI						H-RNTI								OPTIONAL,
		newPrimary-E-RNTI				E-RNTI								OPTIONAL,
		newSecondary-E-RNTI				E-RNTI								OPTIONAL,
		rrc-StateIndicator				RRC-StateIndicator,
		utran-DRX-CycleLengthCoeff		UTRAN-DRX-CycleLengthCoefficient-r7,
		-- TABULAR: If capabilityUpdateRequirement is not present, the default value
		-- defined in 10.3.3.2 shall be used.
		capabilityUpdateRequirement		CapabilityUpdateRequirement-r7		OPTIONAL,
		supportForChangeOfUE-Capability	BOOLEAN,
	-- Specification mode information
		specificationMode				CHOICE {
			complete						SEQUENCE {
				-- Radio bearer IEs
				srb-InformationSetupList		SRB-InformationSetupList2-r7,
				-- Transport channel IEs
				ul-CommonTransChInfo			UL-CommonTransChInfo-r4				OPTIONAL,
				ul-AddReconfTransChInfoList		UL-AddReconfTransChInfoList-r7		OPTIONAL,
				dl-CommonTransChInfo			DL-CommonTransChInfo-r4				OPTIONAL,
				dl-AddReconfTransChInfoList		DL-AddReconfTransChInfoList-r7		OPTIONAL
			},
			preconfiguration				SEQUENCE {
				-- All IEs that include an FDD/TDD choice are split in two IEs for this message,
				-- one for the FDD only elements and one for the TDD only elements, so that one
				-- FDD/TDD choice in this level is sufficient.
				preConfigMode					CHOICE {
					predefinedConfigIdentity		PredefinedConfigIdentity,
					defaultConfig					SEQUENCE {
						defaultConfigMode				DefaultConfigMode,
						defaultConfigIdentity 			DefaultConfigIdentity-r6
					}
				}
			}
		},
	-- Physical channel IEs
		frequencyInfo					FrequencyInfo						OPTIONAL,
		multi-frequencyInfo				Multi-frequencyInfo-LCR-r7			OPTIONAL,
		dtx-drx-TimingInfo				DTX-DRX-TimingInfo-r7				OPTIONAL,
		dtx-drx-Info					DTX-DRX-Info-r7						OPTIONAL,
		hs-scch-LessInfo				HS-SCCH-LessInfo-r7					OPTIONAL,
		maxAllowedUL-TX-Power			MaxAllowedUL-TX-Power				OPTIONAL,
		ul-DPCH-Info					UL-DPCH-Info-r7						OPTIONAL,
		ul-EDCH-Information				UL-EDCH-Information-r7				OPTIONAL,
		dl-HSPDSCH-Information			DL-HSPDSCH-Information-r7			OPTIONAL,
		dl-CommonInformation			DL-CommonInformation-r7				OPTIONAL,
		dl-InformationPerRL-List		DL-InformationPerRL-List-r7			OPTIONAL
}

RRCConnectionSetup-v780ext-IEs ::= SEQUENCE {
	-- Physical channel IEs
		hs-DSCH-TBSizeTable				HS-DSCH-TBSizeTable					OPTIONAL
}

RRCConnectionSetup-v7d0ext-IEs ::= SEQUENCE {
	-- Physical channel IEs
		ul-EDCH-Information				UL-EDCH-Information-ext				OPTIONAL
}

RRCConnectionSetup-r8-IEs ::= SEQUENCE {
	-- TABULAR: Integrity protection shall not be performed on this message.
		activationTime					ActivationTime						OPTIONAL,
		new-U-RNTI						U-RNTI,
		new-c-RNTI						C-RNTI								OPTIONAL,
		new-H-RNTI						H-RNTI								OPTIONAL,
		newPrimary-E-RNTI				E-RNTI								OPTIONAL,
		newSecondary-E-RNTI				E-RNTI								OPTIONAL,
		rrc-StateIndicator				RRC-StateIndicator,
		utran-DRX-CycleLengthCoeff		UTRAN-DRX-CycleLengthCoefficient-r7,
		-- TABULAR: If capabilityUpdateRequirement is not present, the default value
		-- defined in 10.3.3.2 shall be used.
		capabilityUpdateRequirement		CapabilityUpdateRequirement-r8		OPTIONAL,
		supportForChangeOfUE-Capability	BOOLEAN,
	-- Specification mode information
		-- dummy is not used in this version of the specification, it should
		-- not be sent and if received it should be ignored.
		dummy							DefaultConfigForCellFACH			OPTIONAL,
		specificationMode				CHOICE {
			complete						SEQUENCE {
				-- Radio bearer IEs
				srb-InformationSetupList		SRB-InformationSetupList2-r8,
				-- Transport channel IEs
				ul-CommonTransChInfo			UL-CommonTransChInfo-r4				OPTIONAL,
				ul-AddReconfTransChInfoList		UL-AddReconfTransChInfoList-r8		OPTIONAL,
				dl-CommonTransChInfo			DL-CommonTransChInfo-r4				OPTIONAL,
				dl-AddReconfTransChInfoList		DL-AddReconfTransChInfoList-r7		OPTIONAL
			},
			preconfiguration				SEQUENCE {
				-- All IEs that include an FDD/TDD choice are split in two IEs for this message,
				-- one for the FDD only elements and one for the TDD only elements, so that one
				-- FDD/TDD choice in this level is sufficient.
				preConfigMode					CHOICE {
					predefinedConfigIdentity		PredefinedConfigIdentity,
					defaultConfig					SEQUENCE {
						defaultConfigMode				DefaultConfigMode,
						defaultConfigIdentity 			DefaultConfigIdentity-r6
					}
				}
			}
		},
	-- Physical channel IEs
		frequencyInfo					FrequencyInfo						OPTIONAL,
		multi-frequencyInfo				Multi-frequencyInfo-LCR-r7			OPTIONAL,
		dtx-drx-TimingInfo				DTX-DRX-TimingInfo-r7				OPTIONAL,
		dtx-drx-Info					DTX-DRX-Info-r7						OPTIONAL,
		hs-scch-LessInfo				HS-SCCH-LessInfo-r7					OPTIONAL,
		maxAllowedUL-TX-Power			MaxAllowedUL-TX-Power				OPTIONAL,
		ul-DPCH-Info					UL-DPCH-Info-r7						OPTIONAL,
		ul-EDCH-Information				UL-EDCH-Information-r8				OPTIONAL,
		dl-HSPDSCH-Information			DL-HSPDSCH-Information-r8			OPTIONAL,
		dl-CommonInformation			DL-CommonInformation-r8				OPTIONAL,
		dl-InformationPerRL-List		DL-InformationPerRL-List-r8			OPTIONAL,
		dl-SecondaryCellInfoFDD			DL-SecondaryCellInfoFDD				OPTIONAL,
		sps-Information-TDD128			SPS-Information-TDD128-r8			OPTIONAL
}

RRCConnectionSetup-v890ext-IEs ::=	SEQUENCE {
	-- Physical channel IEs
		dl-SecondaryCellInfoFDD-v890ext		DL-SecondaryCellInfoFDD-v890ext		OPTIONAL,
		dl-HSPDSCH-Information				DL-HSPDSCH-Information-r8-ext		OPTIONAL
}

RRCConnectionSetup-v8a0ext-IEs ::= SEQUENCE {
	-- Physical channel IEs
		dl-HSPDSCH-Information				DL-HSPDSCH-Information-r8-ext2		OPTIONAL
}

RRCConnectionSetup-r9-IEs ::= SEQUENCE {
	-- TABULAR: Integrity protection shall not be performed on this message.
		activationTime					ActivationTime						OPTIONAL,
		new-U-RNTI						U-RNTI,
		new-c-RNTI						C-RNTI								OPTIONAL,
		new-H-RNTI						H-RNTI								OPTIONAL,
		newPrimary-E-RNTI				E-RNTI								OPTIONAL,
		newSecondary-E-RNTI				E-RNTI								OPTIONAL,
		rrc-StateIndicator				RRC-StateIndicator,
		utran-DRX-CycleLengthCoeff		UTRAN-DRX-CycleLengthCoefficient-r7,
		-- TABULAR: If capabilityUpdateRequirement is not present, the default value
		-- defined in 10.3.3.2 shall be used.
		capabilityUpdateRequirement		CapabilityUpdateRequirement-r8		OPTIONAL,
		supportForChangeOfUE-Capability	BOOLEAN,
	-- Specification mode information
		defaultConfigForCellFACH		DefaultConfigForCellFACH			OPTIONAL,
		specificationMode				CHOICE {
			complete						SEQUENCE {
				-- Radio bearer IEs
				srb-InformationSetupList		SRB-InformationSetupList2-r8,
				-- Transport channel IEs
				ul-CommonTransChInfo			UL-CommonTransChInfo-r4				OPTIONAL,
				ul-AddReconfTransChInfoList		UL-AddReconfTransChInfoList-r8		OPTIONAL,
				dl-CommonTransChInfo			DL-CommonTransChInfo-r4				OPTIONAL,
				dl-AddReconfTransChInfoList		DL-AddReconfTransChInfoList-r9		OPTIONAL
			},
			preconfiguration				SEQUENCE {
				-- All IEs that include an FDD/TDD choice are split in two IEs for this message,
				-- one for the FDD only elements and one for the TDD only elements, so that one
				-- FDD/TDD choice in this level is sufficient.
				preConfigMode					CHOICE {
					predefinedConfigIdentity		PredefinedConfigIdentity,
					defaultConfig					SEQUENCE {
						defaultConfigMode				DefaultConfigMode,
						defaultConfigIdentity 			DefaultConfigIdentity-r6
					}
				}
			}
		},
	-- Physical channel IEs
		frequencyInfo					FrequencyInfo						OPTIONAL,
		multi-frequencyInfo				Multi-frequencyInfo-LCR-r7			OPTIONAL,
		dtx-drx-TimingInfo				DTX-DRX-TimingInfo-r7				OPTIONAL,
		dtx-drx-Info					DTX-DRX-Info-r7						OPTIONAL,
		hs-scch-LessInfo				HS-SCCH-LessInfo-r7					OPTIONAL,
		maxAllowedUL-TX-Power			MaxAllowedUL-TX-Power				OPTIONAL,
		ul-DPCH-Info					UL-DPCH-Info-r7						OPTIONAL,
		ul-EDCH-Information				UL-EDCH-Information-r9				OPTIONAL,
		dl-HSPDSCH-Information			DL-HSPDSCH-Information-r9			OPTIONAL,
		dl-CommonInformation			DL-CommonInformation-r8				OPTIONAL,
		dl-InformationPerRL-List		DL-InformationPerRL-List-r8			OPTIONAL,
		dl-SecondaryCellInfoFDD			DL-SecondaryCellInfoFDD-r9			OPTIONAL,
		sps-Information-TDD128			SPS-Information-TDD128-r8			OPTIONAL
}

RRCConnectionSetup-v950ext-IEs ::= SEQUENCE {
	-- Physical channel IEs
		secondaryCellMimoParameters		SecondaryCellMIMOparametersFDD-v950ext		OPTIONAL
}

RRCConnectionSetup-r10-IEs ::= SEQUENCE {
	-- TABULAR: Integrity protection shall not be performed on this message.
		activationTime					ActivationTime						OPTIONAL,
		new-U-RNTI						U-RNTI,
		new-c-RNTI						C-RNTI								OPTIONAL,
		new-H-RNTI						H-RNTI								OPTIONAL,
		newPrimary-E-RNTI				E-RNTI								OPTIONAL,
		newSecondary-E-RNTI				E-RNTI								OPTIONAL,
		rrc-StateIndicator				RRC-StateIndicator,
		utran-DRX-CycleLengthCoeff		UTRAN-DRX-CycleLengthCoefficient-r7,
		-- TABULAR: If capabilityUpdateRequirement is not present, the default value
		-- defined in 10.3.3.2 shall be used.
		capabilityUpdateRequirement		CapabilityUpdateRequirement-r8		OPTIONAL,
		supportForChangeOfUE-Capability	BOOLEAN,
	-- Specification mode information
		defaultConfigForCellFACH		DefaultConfigForCellFACH			OPTIONAL,
		specificationMode				CHOICE {
			complete						SEQUENCE {
				-- Radio bearer IEs
				srb-InformationSetupList		SRB-InformationSetupList2-r8,
				-- Transport channel IEs
				ul-CommonTransChInfo			UL-CommonTransChInfo-r4				OPTIONAL,
				ul-AddReconfTransChInfoList		UL-AddReconfTransChInfoList-r8		OPTIONAL,
				dl-CommonTransChInfo			DL-CommonTransChInfo-r4				OPTIONAL,
				dl-AddReconfTransChInfoList		DL-AddReconfTransChInfoList-r9		OPTIONAL
			},
			preconfiguration				SEQUENCE {
				-- All IEs that include an FDD/TDD choice are split in two IEs for this message,
				-- one for the FDD only elements and one for the TDD only elements, so that one
				-- FDD/TDD choice in this level is sufficient.
				preConfigMode					CHOICE {
					predefinedConfigIdentity		PredefinedConfigIdentity,
					defaultConfig					SEQUENCE {
						defaultConfigMode				DefaultConfigMode,
						defaultConfigIdentity 			DefaultConfigIdentity-r6
					}
				}
			}
		},
	-- Physical channel IEs
		frequencyInfo					FrequencyInfo						OPTIONAL,
		multi-frequencyInfo				Multi-frequencyInfo-LCR-r7			OPTIONAL,
		dtx-drx-TimingInfo				DTX-DRX-TimingInfo-r7				OPTIONAL,
		dtx-drx-Info					DTX-DRX-Info-r7						OPTIONAL,
		hs-scch-LessInfo				HS-SCCH-LessInfo-r7					OPTIONAL,
		maxAllowedUL-TX-Power			MaxAllowedUL-TX-Power				OPTIONAL,
		ul-DPCH-Info					UL-DPCH-Info-r7						OPTIONAL,
		ul-EDCH-Information				UL-EDCH-Information-r9				OPTIONAL,
		dl-HSPDSCH-Information			DL-HSPDSCH-Information-r9			OPTIONAL,
		dl-CommonInformation			DL-CommonInformation-r10			OPTIONAL,
		dl-InformationPerRL-List		DL-InformationPerRL-List-r8			OPTIONAL,
		dl-SecondaryCellInfoFDD			DL-SecondaryCellInfoFDD-r10			OPTIONAL,
		additionalDLSecCellInfoListFDD	AdditionalDLSecCellInfoListFDD		OPTIONAL,
		sps-Information-TDD128			SPS-Information-TDD128-r8			OPTIONAL,
		mu-MIMO-Info-TDD128				MU-MIMO-Info-TDD128					OPTIONAL
}

RRCConnectionSetup-r11-IEs ::= SEQUENCE {
	-- TABULAR: Integrity protection shall not be performed on this message.
		activationTime					ActivationTime						OPTIONAL,
		new-U-RNTI						U-RNTI,
		new-c-RNTI						C-RNTI								OPTIONAL,
		new-H-RNTI						H-RNTI								OPTIONAL,
		newPrimary-E-RNTI				E-RNTI								OPTIONAL,
		newSecondary-E-RNTI				E-RNTI								OPTIONAL,
		rrc-StateIndicator				RRC-StateIndicator,
		utran-DRX-CycleLengthCoeff		UTRAN-DRX-CycleLengthCoefficient-r7,
		-- TABULAR: If capabilityUpdateRequirement is not present, the default value
		-- defined in 10.3.3.2 shall be used.
		capabilityUpdateRequirement		CapabilityUpdateRequirement-r8		OPTIONAL,
		supportForChangeOfUE-Capability	BOOLEAN,
	-- Specification mode information
		defaultConfigForCellFACH		DefaultConfigForCellFACH			OPTIONAL,
		specificationMode				CHOICE {
			complete						SEQUENCE {
				-- Radio bearer IEs
				srb-InformationSetupList		SRB-InformationSetupList2-r8,
				-- Transport channel IEs
				ul-CommonTransChInfo			UL-CommonTransChInfo-r4				OPTIONAL,
				ul-AddReconfTransChInfoList		UL-AddReconfTransChInfoList-r8		OPTIONAL,
				dl-CommonTransChInfo			DL-CommonTransChInfo-r4				OPTIONAL,
				dl-AddReconfTransChInfoList		DL-AddReconfTransChInfoList-r11		OPTIONAL
			},
			preconfiguration				SEQUENCE {
				-- All IEs that include an FDD/TDD choice are split in two IEs for this message,
				-- one for the FDD only elements and one for the TDD only elements, so that one
				-- FDD/TDD choice in this level is sufficient.
				preConfigMode					CHOICE {
					predefinedConfigIdentity		PredefinedConfigIdentity,
					defaultConfig					SEQUENCE {
						defaultConfigMode				DefaultConfigMode,
						defaultConfigIdentity 			DefaultConfigIdentity-r6
					}
				}
			}
		},
	-- Physical channel IEs
		frequencyInfo					FrequencyInfo						OPTIONAL,
		multi-frequencyInfo				Multi-frequencyInfo-LCR-r7			OPTIONAL,
		dtx-drx-TimingInfo				DTX-DRX-TimingInfo-r7				OPTIONAL,
		dtx-drx-Info					DTX-DRX-Info-r7						OPTIONAL,
		hs-scch-LessInfo				HS-SCCH-LessInfo-r7					OPTIONAL,
		maxAllowedUL-TX-Power			MaxAllowedUL-TX-Power				OPTIONAL,
		ul-DPCH-Info					UL-DPCH-Info-r11						OPTIONAL,
		ul-EDCH-Information				UL-EDCH-Information-r11				OPTIONAL,
		dl-HSPDSCH-Information			DL-HSPDSCH-Information-r11			OPTIONAL,
		dl-CommonInformation			DL-CommonInformation-r10			OPTIONAL,
		dl-InformationPerRL-List		DL-InformationPerRL-List-r8			OPTIONAL,
		dl-SecondaryCellInfoFDD			DL-SecondaryCellInfoFDD-r11			OPTIONAL,
		additionalDLSecCellInfoListFDD	AdditionalDLSecCellInfoListFDD-r11	OPTIONAL,
		commonERGCHInfoFDD				CommonERGCHInfoFDD					OPTIONAL,
		sps-Information-TDD128			SPS-Information-TDD128-r8			OPTIONAL,
		mu-MIMO-Info-TDD128				MU-MIMO-Info-TDD128					OPTIONAL
}

-- ***************************************************
--
-- RRC CONNECTION SETUP COMPLETE
--
-- ***************************************************

RRCConnectionSetupComplete ::= SEQUENCE {
	-- TABULAR: Integrity protection shall not be performed on this message.
	-- User equipment IEs
		rrc-TransactionIdentifier		RRC-TransactionIdentifier,
		startList						STARTList,
		ue-RadioAccessCapability		UE-RadioAccessCapability			OPTIONAL,
	--	Other IEs
		ue-RATSpecificCapability		InterRAT-UE-RadioAccessCapabilityList	OPTIONAL,
	-- Non critical extensions
		v370NonCriticalExtensions			SEQUENCE {
			rrcConnectionSetupComplete-v370ext	RRCConnectionSetupComplete-v370ext,
			v380NonCriticalExtensions			SEQUENCE {
				rrcConnectionSetupComplete-v380ext	RRCConnectionSetupComplete-v380ext-IEs,
				-- Reserved for future non critical extension
				v3a0NonCriticalExtensions			SEQUENCE {
					rrcConnectionSetupComplete-v3a0ext	RRCConnectionSetupComplete-v3a0ext-IEs,
					laterNonCriticalExtensions			SEQUENCE {
						-- Container for additional R99 extensions
						rrcConnectionSetupComplete-r3-add-ext		BIT STRING
								(CONTAINING RRCConnectionSetupComplete-r3-add-ext-IEs)	OPTIONAL,
						v3g0NonCriticalExtensions			SEQUENCE {
							rrcConnectionSetupComplete-v3g0ext	RRCConnectionSetupComplete-v3g0ext-IEs,
							v4b0NonCriticalExtensions			SEQUENCE {
								rrcConnectionSetupComplete-v4b0ext
																RRCConnectionSetupComplete-v4b0ext-IEs,
								v590NonCriticalExtensions			SEQUENCE {
									rrcConnectionSetupComplete-v590ext
																RRCConnectionSetupComplete-v590ext-IEs,
									v5c0NonCriticalExtensions			SEQUENCE {
										rrcConnectionSetupComplete-v5c0ext
																RRCConnectionSetupComplete-v5c0ext-IEs,
										v690NonCriticalExtensions			SEQUENCE {
											rrcConnectionSetupComplete-v690ext
																RRCConnectionSetupComplete-v690ext-IEs,
											v770NonCriticalExtensions		SEQUENCE {
												rrcConectionSetupComplete-v770ext
																RRCConnectionSetupComplete-v770ext-IEs,
												va40NonCriticalExtensions		SEQUENCE {
													rrcConectionSetupComplete-va40ext
																RRCConnectionSetupComplete-va40ext-IEs,
													vb50NonCriticalExtensions		SEQUENCE {
														rrcConnectionSetupComplete-vb50ext
																RRCConnectionSetupComplete-vb50ext-IEs,
														nonCriticalExtensions	SEQUENCE {}	OPTIONAL
													}		OPTIONAL
												}		OPTIONAL
											}		OPTIONAL
										}		OPTIONAL
									}		OPTIONAL
								}		OPTIONAL
							}		OPTIONAL
						}		OPTIONAL
					}		OPTIONAL
				}		OPTIONAL
			}		OPTIONAL
		}		OPTIONAL
}

RRCConnectionSetupComplete-v370ext ::= SEQUENCE {
	-- User equipment IEs
		ue-RadioAccessCapability-v370ext	UE-RadioAccessCapability-v370ext	OPTIONAL
}

RRCConnectionSetupComplete-v380ext-IEs ::= SEQUENCE {
	-- User equipment IEs
		ue-RadioAccessCapability-v380ext	UE-RadioAccessCapability-v380ext		OPTIONAL,
		dl-PhysChCapabilityFDD-v380ext		DL-PhysChCapabilityFDD-v380ext
}

RRCConnectionSetupComplete-v3a0ext-IEs ::= SEQUENCE {
	-- User equipment IEs
		ue-RadioAccessCapability-v3a0ext	UE-RadioAccessCapability-v3a0ext	OPTIONAL
}

RRCConnectionSetupComplete-v3g0ext-IEs ::= SEQUENCE {
	-- User equipment IEs
		ue-RadioAccessCapability-v3g0ext	UE-RadioAccessCapability-v3g0ext	OPTIONAL
}

RRCConnectionSetupComplete-r3-add-ext-IEs ::= SEQUENCE {
		rrcConnectionSetupComplete-v650ext		RRCConnectionSetupComplete-v650ext-IEs	OPTIONAL,
		v680NonCriticalExtensions				SEQUENCE {
			rrcConnectionSetupComplete-v680ext		RRCConnectionSetupComplete-v680ext-IEs,
			v7e0NonCriticalExtensions				SEQUENCE {
				rrcConnectionSetupComplete-v7e0ext		RRCConnectionSetupComplete-v7e0ext-IEs,
				v7f0NonCriticalExtensions				SEQUENCE {
					rrcConnectionSetupComplete-v7f0ext
														RRCConnectionSetupComplete-v7f0ext-IEs,
					va40NonCriticalExtensions					SEQUENCE {
						rrcConnectionSetupCompleteBand-va40ext
														RRCConnectionSetupCompleteBand-va40ext-IEs,
						nonCriticalExtensions			SEQUENCE {}	OPTIONAL 
					}		OPTIONAL
				}		OPTIONAL
			}		OPTIONAL
		}		OPTIONAL
}

RRCConnectionSetupComplete-v4b0ext-IEs ::= SEQUENCE {
	-- User equipment IEs
		ue-RadioAccessCapability-v4b0ext		UE-RadioAccessCapability-v4b0ext		OPTIONAL
}

RRCConnectionSetupComplete-v590ext-IEs ::= SEQUENCE {
	-- User equipment IEs
		ue-RadioAccessCapability-v590ext		UE-RadioAccessCapability-v590ext		OPTIONAL,
	-- Other IEs
		ue-RATSpecificCapability-v590ext		InterRAT-UE-RadioAccessCapability-v590ext	OPTIONAL
}

RRCConnectionSetupComplete-v5c0ext-IEs ::= SEQUENCE {
	-- User equipment IEs
		ue-RadioAccessCapability-v5c0ext		UE-RadioAccessCapability-v5c0ext		OPTIONAL
}

RRCConnectionSetupComplete-v650ext-IEs ::= SEQUENCE {
	-- User equipment IEs
		ue-RadioAccessCapability-v650ext		UE-RadioAccessCapability-v650ext
}

RRCConnectionSetupComplete-v680ext-IEs ::= SEQUENCE {
	-- User equipment IEs
		ue-RadioAccessCapability-v680ext		UE-RadioAccessCapability-v680ext
}

RRCConnectionSetupComplete-v690ext-IEs ::= SEQUENCE {
	-- User equipment IEs
		ueCapabilityContainer				BIT STRING
												(CONTAINING UE-CapabilityContainer-IEs)	OPTIONAL
}

RRCConnectionSetupComplete-v770ext-IEs ::= SEQUENCE {
	-- Other IEs
		deferredMeasurementControlReading	ENUMERATED { true }						OPTIONAL
}

RRCConnectionSetupComplete-v7e0ext-IEs ::= SEQUENCE {
	-- User equipment IEs
		ue-RadioAccessCapability				UE-RadioAccessCapability-v7e0ext
}

RRCConnectionSetupComplete-v7f0ext-IEs ::= SEQUENCE {
	-- User equipment IEs
		ue-RadioAccessCapability				UE-RadioAccessCapability-v7f0ext	OPTIONAL
}

RRCConnectionSetupComplete-va40ext-IEs ::= SEQUENCE {
	-- Other IEs
		loggedMeasAvailable							ENUMERATED { true }					OPTIONAL,
		loggedANRResultsAvailable					ENUMERATED { true }					OPTIONAL}

RRCConnectionSetupCompleteBand-va40ext-IEs ::= SEQUENCE {
	-- User equipment IEs
		ue-RadioAccessCapabBand					UE-RadioAccessCapabBand-va40ext		OPTIONAL
}

RRCConnectionSetupComplete-vb50ext-IEs ::= SEQUENCE {
	-- Other IEs
		connEstFailInfoAvailable			ENUMERATED { true }	OPTIONAL
}

-- ***************************************************
--
-- RRC FAILURE INFO
--
-- ***************************************************

RRC-FailureInfo ::= CHOICE {
	r3											SEQUENCE {
		rRC-FailureInfo-r3							RRC-FailureInfo-r3-IEs,
		laterNonCriticalExtensions		SEQUENCE {
			-- Container for additional R99 extensions
			rrc-FailureInfo-r3-add-ext		BIT STRING		OPTIONAL,
			nonCriticalExtensions						SEQUENCE {}	OPTIONAL
		}	OPTIONAL
	},
	criticalExtensions							SEQUENCE {}
}

RRC-FailureInfo-r3-IEs ::=		SEQUENCE {
	-- Non-RRC IEs
		failureCauseWithProtErr							FailureCauseWithProtErr
}

-- ***************************************************
--
-- RRC STATUS
--
-- ***************************************************

RRCStatus ::= SEQUENCE {
	-- Other IEs
		-- TABULAR: Identification of received message is nested in
		-- ProtocolErrorMoreInformation
		protocolErrorInformation		ProtocolErrorMoreInformation,
		laterNonCriticalExtensions		SEQUENCE {
			-- Container for additional R99 extensions
			rrcStatus-r3-add-ext		BIT STRING		OPTIONAL,
			nonCriticalExtensions			SEQUENCE {}		OPTIONAL
		}	OPTIONAL
}

-- ***************************************************
--
-- SECURITY MODE COMMAND
--
-- ***************************************************

SecurityModeCommand ::= CHOICE {
	r3								SEQUENCE {
		securityModeCommand-r3			SecurityModeCommand-r3-IEs,
		laterNonCriticalExtensions		SEQUENCE {
			-- Container for additional R99 extensions
			securityModeCommand-r3-add-ext		BIT STRING		OPTIONAL,
			nonCriticalExtensions			SEQUENCE {}		OPTIONAL
		}	OPTIONAL
	},
	later-than-r3					SEQUENCE {
		rrc-TransactionIdentifier		RRC-TransactionIdentifier,
		criticalExtensions				CHOICE {
			r7								SEQUENCE{
				securityModeCommand-r7			SecurityModeCommand-r7-IEs,
				-- Container for adding non critical extensions after freezing REL-8
				securityModeCommand-r7-add-ext	BIT STRING		OPTIONAL,
				nonCriticalExtensions			SEQUENCE {}		OPTIONAL
			},
			criticalExtensions				SEQUENCE {}
		}
	}
}

SecurityModeCommand-r3-IEs ::= SEQUENCE {
-- TABULAR: Integrity protection shall always be performed on this message.
	-- User equipment IEs
		rrc-TransactionIdentifier		RRC-TransactionIdentifier,
		securityCapability				SecurityCapability,
		cipheringModeInfo				CipheringModeInfo					OPTIONAL,
		integrityProtectionModeInfo		IntegrityProtectionModeInfo			OPTIONAL,
	-- Core network IEs
		cn-DomainIdentity				CN-DomainIdentity,
	-- Other IEs
		ue-SystemSpecificSecurityCap	InterRAT-UE-SecurityCapList			OPTIONAL
}

SecurityModeCommand-r7-IEs ::= SEQUENCE {
-- TABULAR: Integrity protection shall always be performed on this message.
	-- User equipment IEs
		securityCapability				SecurityCapability,
		cipheringModeInfo				CipheringModeInfo-r7				OPTIONAL,
		integrityProtectionModeInfo		IntegrityProtectionModeInfo-r7		OPTIONAL,
	-- Core network IEs
		cn-DomainIdentity				CN-DomainIdentity,
	-- Other IEs
		ue-SystemSpecificSecurityCap	InterRAT-UE-SecurityCapList			OPTIONAL
}

-- ***************************************************
--
-- SECURITY MODE COMPLETE
--
-- ***************************************************

SecurityModeComplete ::= SEQUENCE {
-- TABULAR: Integrity protection shall always be performed on this message.

	-- User equipment IEs
		rrc-TransactionIdentifier		RRC-TransactionIdentifier,
		ul-IntegProtActivationInfo		IntegrityProtActivationInfo			OPTIONAL,
	-- Radio bearer IEs
		rb-UL-CiphActivationTimeInfo	RB-ActivationTimeInfoList			OPTIONAL,
		laterNonCriticalExtensions		SEQUENCE {
			-- Container for additional R99 extensions
			securityModeComplete-r3-add-ext		BIT STRING		OPTIONAL,
			nonCriticalExtensions			SEQUENCE {}		OPTIONAL
		}	OPTIONAL
}

-- ***************************************************
--
-- SECURITY MODE FAILURE
--
-- ***************************************************

SecurityModeFailure ::= SEQUENCE {
	-- User equipment IEs
		rrc-TransactionIdentifier		RRC-TransactionIdentifier,
		failureCause					FailureCauseWithProtErr,
		laterNonCriticalExtensions		SEQUENCE {
			-- Container for additional R99 extensions
			securityModeFailure-r3-add-ext		BIT STRING		OPTIONAL,
			nonCriticalExtensions			SEQUENCE {}		OPTIONAL
		}	OPTIONAL
}

-- ***************************************************
--
-- SIGNALLING CONNECTION RELEASE
--
-- ***************************************************

SignallingConnectionRelease ::= CHOICE {
	r3								SEQUENCE {
		signallingConnectionRelease-r3	SignallingConnectionRelease-r3-IEs,
		laterNonCriticalExtensions		SEQUENCE {
			-- Container for additional R99 extensions
			signallingConnectionRelease-r3-add-ext		BIT STRING		OPTIONAL,
			va40NonCriticalExtensions			SEQUENCE {
				signallingConnectionRelease-va40ext		SignallingConnectionRelease-va40ext-IEs,
			nonCriticalExtensions			SEQUENCE {}		OPTIONAL
			}	OPTIONAL
		}	OPTIONAL
	},
	later-than-r3					SEQUENCE {
		rrc-TransactionIdentifier		RRC-TransactionIdentifier,
		criticalExtensions				SEQUENCE {}
	}
}

SignallingConnectionRelease-r3-IEs ::= SEQUENCE {
	-- User equipment IEs
		rrc-TransactionIdentifier		RRC-TransactionIdentifier,
	-- Core network IEs
		cn-DomainIdentity				CN-DomainIdentity
}

SignallingConnectionRelease-va40ext-IEs ::= SEQUENCE {
	extendedWaitTime 				ExtendedWaitTime					OPTIONAL
}

-- ***************************************************
--
-- SIGNALLING CONNECTION RELEASE INDICATION
--
-- ***************************************************

SignallingConnectionReleaseIndication ::= SEQUENCE {
	-- Core network IEs
		cn-DomainIdentity				CN-DomainIdentity,
		laterNonCriticalExtensions		SEQUENCE {
			-- Container for additional R99 extensions
			signallingConnectionReleaseIndication-r3-add-ext		BIT STRING		OPTIONAL,
			v860nonCriticalExtentions		SEQUENCE {
				signallingConnectionReleaseIndication-v860ext
												SignallingConnectionReleaseIndication-v860ext,
				nonCriticalExtensions			SEQUENCE {}		OPTIONAL
			}	OPTIONAL
		}	OPTIONAL
}

SignallingConnectionReleaseIndication-v860ext ::= SEQUENCE {
		signallingConnectionReleaseIndicationCause
										ENUMERATED { uERequestedPSDataSessionEnd, anyOtherCause }
}

-- ***************************************************
--
-- SYSTEM INFORMATION for BCH
--
-- ***************************************************

SystemInformation-BCH ::= SEQUENCE {
	-- Other information elements
		sfn-Prime						SFN-Prime,
		payload 						CHOICE {
			noSegment						NULL,
			firstSegment					FirstSegment,
			subsequentSegment				SubsequentSegment,
			lastSegmentShort						LastSegmentShort,
			lastAndFirst					SEQUENCE {
				lastSegmentShort				LastSegmentShort,
				firstSegment					FirstSegmentShort
			},
			lastAndComplete					SEQUENCE {
				lastSegmentShort				LastSegmentShort,
				completeSIB-List				CompleteSIB-List
			},
			lastAndCompleteAndFirst			SEQUENCE {
				lastSegmentShort				LastSegmentShort,
				completeSIB-List				CompleteSIB-List,
				firstSegment					FirstSegmentShort
			},
			completeSIB-List				CompleteSIB-List,
			completeAndFirst				SEQUENCE {
				completeSIB-List				CompleteSIB-List,
				firstSegment					FirstSegmentShort
			},
			completeSIB						CompleteSIB,
			lastSegment						LastSegment,
			spare5							NULL,
			spare4							NULL,
			spare3							NULL,
			spare2							NULL,
			spare1							NULL
		}
}

-- ***************************************************
--
-- SYSTEM INFORMATION for FACH
--
-- ***************************************************

-- this IE is not used in this version of the specification.
SystemInformation-FACH ::= SEQUENCE {
	-- Other information elements
		payload 						CHOICE {
			noSegment						NULL,
			firstSegment					FirstSegment,
			subsequentSegment				SubsequentSegment,
			lastSegmentShort				LastSegmentShort,
			lastAndFirst					SEQUENCE {
				lastSegmentShort				LastSegmentShort,
				firstSegment					FirstSegmentShort
			},
			lastAndComplete					SEQUENCE {
				lastSegmentShort				LastSegmentShort,
				completeSIB-List				CompleteSIB-List
			},
			lastAndCompleteAndFirst			SEQUENCE {
				lastSegmentShort				LastSegmentShort,
				completeSIB-List				CompleteSIB-List,
				firstSegment					FirstSegmentShort
			},
			completeSIB-List				CompleteSIB-List,
			completeAndFirst				SEQUENCE {
				completeSIB-List				CompleteSIB-List,
				firstSegment					FirstSegmentShort
			},
			completeSIB						CompleteSIB,
			lastSegment						LastSegment,
			spare5							NULL,
			spare4							NULL,
			spare3							NULL,
			spare2							NULL,
			spare1							NULL
		}
}

-- ***************************************************
--
-- First segment
--
-- ***************************************************

FirstSegment ::=					SEQUENCE {
	-- Other information elements
		sib-Type						SIB-Type,
		seg-Count						SegCount,
		sib-Data-fixed					SIB-Data-fixed
}

-- ***************************************************
--
-- First segment (short)
--
-- ***************************************************

FirstSegmentShort ::=				SEQUENCE {
	-- Other information elements
		sib-Type						SIB-Type,
		seg-Count						SegCount,
		sib-Data-variable				SIB-Data-variable
}

-- ***************************************************
--
-- Subsequent segment
--
-- ***************************************************

SubsequentSegment ::=				SEQUENCE {
	-- Other information elements
		sib-Type						SIB-Type,
		segmentIndex					SegmentIndex,
		sib-Data-fixed					SIB-Data-fixed
}

-- ***************************************************
--
-- Last segment
--
-- ***************************************************

LastSegment ::=						SEQUENCE {
	-- Other information elements
		sib-Type						SIB-Type,
		segmentIndex					SegmentIndex,
		-- For sib-Data-fixed, in case the SIB data is less than 222 bits, padding
		-- shall be used. The same padding bits shall be used as defined in clause 12.1
		sib-Data-fixed					SIB-Data-fixed
}

LastSegmentShort ::=						SEQUENCE {
	-- Other information elements
		sib-Type						SIB-Type,
		segmentIndex					SegmentIndex,
		sib-Data-variable				SIB-Data-variable
}

-- ***************************************************
--
-- Complete SIB
--
-- ***************************************************

CompleteSIB-List ::=				SEQUENCE (SIZE (1..maxSIBperMsg)) OF
										CompleteSIBshort

CompleteSIB ::=						SEQUENCE {
	-- Other information elements
		sib-Type						SIB-Type,
		-- For sib-Data-fixed, in case the SIB data is less than 226 bits, padding
		-- shall be used. The same padding bits shall be used as defined in clause 12.1
		sib-Data-fixed					BIT STRING (SIZE (226))
}

CompleteSIBshort ::=						SEQUENCE {
	-- Other information elements
		sib-Type						SIB-Type,
		sib-Data-variable				SIB-Data-variable
}

-- ***************************************************
--
-- SYSTEM INFORMATION CHANGE INDICATION
--
-- ***************************************************

SystemInformationChangeIndication ::= 	SEQUENCE {
	-- Other IEs
		bcch-ModificationInfo				BCCH-ModificationInfo,
		laterNonCriticalExtensions			SEQUENCE {
			-- Container for additional R99 extensions
			systemInformationChangeIndication-r3-add-ext		BIT STRING		OPTIONAL,
			v860NonCriticalExtensions		SEQUENCE {
				systemInformationChangeIndication-v860ext
												SystemInformationChangeIndication-v860ext-IEs,
				nonCriticalExtensions			SEQUENCE {}		OPTIONAL
			}	OPTIONAL
		}	OPTIONAL
}

SystemInformationChangeIndication-v860ext-IEs ::= SEQUENCE {
	-- Other IEs
		etws-Information					ETWS-Information					OPTIONAL
}

-- ***************************************************
--
-- TRANSPORT CHANNEL RECONFIGURATION
--
-- ***************************************************

TransportChannelReconfiguration ::= CHOICE {
	r3								SEQUENCE {
		transportChannelReconfiguration-r3
										TransportChannelReconfiguration-r3-IEs,
		v3a0NonCriticalExtensions		SEQUENCE {
			transportChannelReconfiguration-v3a0ext
											TransportChannelReconfiguration-v3a0ext,
			laterNonCriticalExtensions			SEQUENCE {
				-- Container for additional R99 extensions
				transportChannelReconfiguration-r3-add-ext		BIT STRING		OPTIONAL,
				v4b0NonCriticalExtensions		SEQUENCE {
					transportChannelReconfiguration-v4b0ext	
													TransportChannelReconfiguration-v4b0ext-IEs,
					v590NonCriticalExtensions		SEQUENCE {
						transportChannelReconfiguration-v590ext	
														TransportChannelReconfiguration-v590ext-IEs,
						v690NonCriticalExtensions		SEQUENCE {
							transportChannelReconfiguration-v690ext	
														TransportChannelReconfiguration-v690ext-IEs,
							v770NonCriticalExtensions		SEQUENCE {
								transportChannelReconfiguration-v770ext
														TransportChannelReconfiguration-v770ext-IEs,
								nonCriticalExtensions			SEQUENCE {}		OPTIONAL
							}		OPTIONAL
						}		OPTIONAL
					}		OPTIONAL
				}		OPTIONAL
			}		OPTIONAL
		}		OPTIONAL
	},
	later-than-r3					SEQUENCE {
		rrc-TransactionIdentifier		RRC-TransactionIdentifier,
		criticalExtensions				CHOICE {
			r4								SEQUENCE {
				transportChannelReconfiguration-r4
												TransportChannelReconfiguration-r4-IEs,
				v4d0NonCriticalExtensions			SEQUENCE {
					-- Container for adding non critical extensions after freezing REL-5
					transportChannelReconfiguration-r4-add-ext		BIT STRING		OPTIONAL,
					v590NonCriticalExtensions		SEQUENCE {
						transportChannelReconfiguration-v590ext	
													TransportChannelReconfiguration-v590ext-IEs,
						v690NonCriticalExtensions		SEQUENCE {
							transportChannelReconfiguration-v690ext	
														TransportChannelReconfiguration-v690ext-IEs,
							v770NonCriticalExtensions		SEQUENCE {
								transportChannelReconfiguration-v770ext
														TransportChannelReconfiguration-v770ext-IEs,
								nonCriticalExtensions			SEQUENCE {}		OPTIONAL
							}	OPTIONAL
						}	OPTIONAL
					}	OPTIONAL
				}	OPTIONAL
			},
			criticalExtensions				CHOICE {
				r5								SEQUENCE {
					transportChannelReconfiguration-r5
													TransportChannelReconfiguration-r5-IEs,
					-- Container for adding non critical extensions after freezing REL-6
					transportChannelReconfiguration-r5-add-ext		BIT STRING		OPTIONAL,
					v690NonCriticalExtensions		SEQUENCE {
						transportChannelReconfiguration-v690ext	
														TransportChannelReconfiguration-v690ext-IEs,
						v770NonCriticalExtensions		SEQUENCE {
								transportChannelReconfiguration-v770ext
														TransportChannelReconfiguration-v770ext-IEs,
							nonCriticalExtensions			SEQUENCE {}		OPTIONAL
						}	OPTIONAL
					}	OPTIONAL
				},
				criticalExtensions				CHOICE {
					r6								SEQUENCE {
						transportChannelReconfiguration-r6
														TransportChannelReconfiguration-r6-IEs,
						-- Container for adding non critical extensions after freezing REL-7
						transportChannelReconfiguration-r6-add-ext		BIT STRING		OPTIONAL,
						v6b0NonCriticalExtensions		SEQUENCE {
							transportChannelReconfiguration-v6b0ext
														TransportChannelReconfiguration-v6b0ext-IEs,
							v770NonCriticalExtensions		SEQUENCE {
								transportChannelReconfiguration-v770ext
														TransportChannelReconfiguration-v770ext-IEs,
								nonCriticalExtensions			SEQUENCE {}		OPTIONAL
							}	OPTIONAL
						}	OPTIONAL
					},
					criticalExtensions				CHOICE {
						r7								SEQUENCE {
							transportChannelReconfiguration-r7
														TransportChannelReconfiguration-r7-IEs,
							-- Container for adding non critical extensions after freezing REL-8
							transportChannelReconfiguration-r7-add-ext		BIT STRING	OPTIONAL,
							v780NonCriticalExtensions		SEQUENCE {
								transportChannelReconfiguration-v780ext
														TransportChannelReconfiguration-v780ext-IEs,
								v7d0NonCriticalExtensions		SEQUENCE {
									transportChannelReconfiguration-v7d0ext
														TransportChannelReconfiguration-v7d0ext-IEs,
									v7f0NonCriticalExtensions		SEQUENCE {
										transportChannelReconfiguration-v7f0ext
														TransportChannelReconfiguration-v7f0ext-IEs,
										v7g0NonCriticalExtensions		SEQUENCE {
											transportChannelReconfiguration-v7g0ext
														TransportChannelReconfiguration-v7g0ext-IEs,
											nonCriticalExtensions			SEQUENCE {}		OPTIONAL
										}	OPTIONAL
									}	OPTIONAL
								}	OPTIONAL
							}	OPTIONAL
						},
						criticalExtensions				CHOICE {
							r8								SEQUENCE {
								transportChannelReconfiguration-r8
															TransportChannelReconfiguration-r8-IEs,
								-- Container for adding non critical extensions after freezing REL-9
								transportChannelReconfiguration-r8-add-ext
																BIT STRING		OPTIONAL,
								v7d0NonCriticalExtensions		SEQUENCE {
									transportChannelReconfiguration-v7d0ext
														TransportChannelReconfiguration-v7d0ext-IEs,
									v7f0NonCriticalExtensions		SEQUENCE {
										transportChannelReconfiguration-v7f0ext
														TransportChannelReconfiguration-v7f0ext-IEs,
										v890NonCriticalExtensions		SEQUENCE {
											transportChannelReconfiguration-v890ext
													TransportChannelReconfiguration-v890ext-IEs,
											v7g0NonCriticalExtensions		SEQUENCE {
												transportChannelReconfiguration-v7g0ext
													TransportChannelReconfiguration-v7g0ext-IEs,
												v8a0NonCriticalExtensions		SEQUENCE {
													transportChannelReconfiguration-v8a0ext
														TransportChannelReconfiguration-v8a0ext-IEs,
													nonCriticalExtensions			
														SEQUENCE {}		OPTIONAL
												}	OPTIONAL
											}	OPTIONAL
										}	OPTIONAL
									}	OPTIONAL
								}	OPTIONAL
							},
							criticalExtensions				CHOICE {
								r9								SEQUENCE {
									transportChannelReconfiguration-r9
															TransportChannelReconfiguration-r9-IEs,
									-- Container for adding non critical extensions after 
									-- freezing REL-10
									transportChannelReconfiguration-r9-add-ext
																	BIT STRING		OPTIONAL,
									v950NonCriticalExtensions		SEQUENCE {
										transportChannelReconfiguration-v950ext
														TransportChannelReconfiguration-v950ext-IEs,
										v9c0NonCriticalExtensions		SEQUENCE {
											transportChannelReconfiguration-v9c0ext
														TransportChannelReconfiguration-v9c0ext-IEs,
											nonCriticalExtensions			SEQUENCE {}		OPTIONAL
										}	OPTIONAL
									}	OPTIONAL
								},
								criticalExtensions				CHOICE {
									r10								SEQUENCE {
										transportChannelReconfiguration-r10
															TransportChannelReconfiguration-r10-IEs,
										-- Container for adding non critical extensions after 
										-- freezing REL-11
										transportChannelReconfiguration-r10-add-ext
																		BIT STRING		OPTIONAL,
										v9c0NonCriticalExtensions		SEQUENCE {
											transportChannelReconfiguration-v9c0ext
														TransportChannelReconfiguration-v9c0ext-IEs,
											vb50NonCriticalExtensions		SEQUENCE {
												transportChannelReconfiguration-vb50ext
														TransportChannelReconfiguration-vb50ext-IEs,
											nonCriticalExtensions			SEQUENCE {}		OPTIONAL
											}	OPTIONAL
										}	OPTIONAL
									},
									criticalExtensions				CHOICE {
										r11								SEQUENCE {
											transportChannelReconfiguration-r11
															TransportChannelReconfiguration-r11-IEs,
											-- Container for adding non critical extensions after 
											-- freezing REL-12
											transportChannelReconfiguration-r11-add-ext
																		BIT STRING		OPTIONAL,
											nonCriticalExtensions			SEQUENCE {}		OPTIONAL
										},
										criticalExtensions				SEQUENCE {}
									}
								}
							}
						}
					}
				}
			}
		}
	}
}

TransportChannelReconfiguration-r3-IEs ::= SEQUENCE {
	-- User equipment IEs
		rrc-TransactionIdentifier		RRC-TransactionIdentifier,
		integrityProtectionModeInfo		IntegrityProtectionModeInfo			OPTIONAL,
		cipheringModeInfo				CipheringModeInfo					OPTIONAL,
		activationTime					ActivationTime						OPTIONAL,
		new-U-RNTI						U-RNTI								OPTIONAL,
		new-C-RNTI						C-RNTI								OPTIONAL,
		rrc-StateIndicator				RRC-StateIndicator,
		utran-DRX-CycleLengthCoeff		UTRAN-DRX-CycleLengthCoefficient	OPTIONAL,
	-- Core network IEs
		cn-InformationInfo				CN-InformationInfo					OPTIONAL,
	-- UTRAN mobility IEs
		ura-Identity					URA-Identity						OPTIONAL,
	-- Radio bearer IEs
		dl-CounterSynchronisationInfo	DL-CounterSynchronisationInfo		OPTIONAL,
	-- Transport channel IEs
		ul-CommonTransChInfo			UL-CommonTransChInfo				OPTIONAL,
		ul-AddReconfTransChInfoList		UL-AddReconfTransChInfoList			OPTIONAL,
		-- 'dummy', 'dummy1' and 'dummy2' are not used in this version of the specification,
		-- they should not be sent and if received they should be ignored.
		dummy							CHOICE {
			fdd								SEQUENCE {
				dummy1							CPCH-SetID					OPTIONAL,
				dummy2							DRAC-StaticInformationList	OPTIONAL
			},
			tdd								NULL
		}																	OPTIONAL,
		dl-CommonTransChInfo			DL-CommonTransChInfo				OPTIONAL,
		dl-AddReconfTransChInfoList		DL-AddReconfTransChInfoList			OPTIONAL,
	-- Physical channel IEs
		frequencyInfo					FrequencyInfo						OPTIONAL,
		maxAllowedUL-TX-Power			MaxAllowedUL-TX-Power				OPTIONAL,
		ul-ChannelRequirement			UL-ChannelRequirement				OPTIONAL,
		modeSpecificPhysChInfo			CHOICE {
			fdd								SEQUENCE {
				-- dummy is not used in this version of specification, it should
				-- not be sent and if received it should be ignored.
				dummy							DL-PDSCH-Information		OPTIONAL
			},
			tdd							NULL
		},
		dl-CommonInformation			DL-CommonInformation				OPTIONAL,
		dl-InformationPerRL-List		DL-InformationPerRL-List			OPTIONAL
}

TransportChannelReconfiguration-v3a0ext ::= SEQUENCE {
	-- The IE "new-DSCH-RNTI" should not be included in FDD mode, and if received
	-- the UE behaviour is unspecified
	new-DSCH-RNTI					DSCH-RNTI							OPTIONAL
}

TransportChannelReconfiguration-v4b0ext-IEs ::= SEQUENCE {
	-- Physical channel IEs
		-- dummy is not used in this version of the specification, it should
		-- not be sent and if received it should be ignored.
		dummy								SSDT-UL								OPTIONAL,
		-- The order of the RLs in IE cell-id-PerRL-List is the same as
		-- in IE DL-InformationPerRL-List included in this message
		cell-id-PerRL-List					CellIdentity-PerRL-List				OPTIONAL
}

TransportChannelReconfiguration-v590ext-IEs ::= SEQUENCE {
	-- Physical channel IEs
		dl-TPC-PowerOffsetPerRL-List	DL-TPC-PowerOffsetPerRL-List		OPTIONAL
}

TransportChannelReconfiguration-r4-IEs ::= SEQUENCE {
	-- User equipment IEs
		integrityProtectionModeInfo		IntegrityProtectionModeInfo			OPTIONAL,
		cipheringModeInfo				CipheringModeInfo					OPTIONAL,
		activationTime					ActivationTime						OPTIONAL,
		new-U-RNTI						U-RNTI								OPTIONAL,
		new-C-RNTI						C-RNTI								OPTIONAL,
		-- The IE "new-DSCH-RNTI" should not be included in FDD mode, and if received
		-- the UE behaviour is unspecified
		new-DSCH-RNTI					DSCH-RNTI							OPTIONAL,
		rrc-StateIndicator				RRC-StateIndicator,
		utran-DRX-CycleLengthCoeff		UTRAN-DRX-CycleLengthCoefficient	OPTIONAL,
	-- Core network IEs
		cn-InformationInfo				CN-InformationInfo					OPTIONAL,
	-- UTRAN mobility IEs
		ura-Identity					URA-Identity						OPTIONAL,
	-- Radio bearer IEs
		dl-CounterSynchronisationInfo	DL-CounterSynchronisationInfo		OPTIONAL,
	-- Transport channel IEs
		ul-CommonTransChInfo			UL-CommonTransChInfo-r4				OPTIONAL,
		ul-AddReconfTransChInfoList		UL-AddReconfTransChInfoList			OPTIONAL,
		-- 'dummy', 'dummy1' and 'dummy2' are not used in this version of the specification,
		-- they should not be sent and if received they should be ignored.
		dummy							CHOICE {
			fdd								SEQUENCE {
				dummy1							CPCH-SetID					OPTIONAL,
				dummy2							DRAC-StaticInformationList	OPTIONAL
			},
			tdd								NULL
		}																	OPTIONAL,
		dl-CommonTransChInfo			DL-CommonTransChInfo-r4				OPTIONAL,
		dl-AddReconfTransChInfoList		DL-AddReconfTransChInfoList-r4		OPTIONAL,
	-- Physical channel IEs
		frequencyInfo					FrequencyInfo						OPTIONAL,
		maxAllowedUL-TX-Power			MaxAllowedUL-TX-Power				OPTIONAL,
		ul-ChannelRequirement			UL-ChannelRequirement-r4			OPTIONAL,
		modeSpecificPhysChInfo			CHOICE {
			fdd								SEQUENCE {
				-- dummy is not used in this version of specification, it should
				-- not be sent and if received it should be ignored.
				dummy							DL-PDSCH-Information		OPTIONAL
			},
			tdd							NULL
		},
		dl-CommonInformation			DL-CommonInformation-r4				OPTIONAL,
		dl-InformationPerRL-List		DL-InformationPerRL-List-r4			OPTIONAL
}

TransportChannelReconfiguration-r5-IEs ::= SEQUENCE {
	-- User equipment IEs
		integrityProtectionModeInfo		IntegrityProtectionModeInfo			OPTIONAL,
		cipheringModeInfo				CipheringModeInfo					OPTIONAL,
		activationTime					ActivationTime						OPTIONAL,
		new-U-RNTI						U-RNTI								OPTIONAL,
		new-C-RNTI						C-RNTI								OPTIONAL,
		-- The IE "new-DSCH-RNTI" should not be included in FDD mode, and if received
		-- the UE behaviour is unspecified
		new-DSCH-RNTI					DSCH-RNTI							OPTIONAL,
		new-H-RNTI						H-RNTI								OPTIONAL,
		rrc-StateIndicator				RRC-StateIndicator,
		utran-DRX-CycleLengthCoeff		UTRAN-DRX-CycleLengthCoefficient	OPTIONAL,
	-- Core network IEs
		cn-InformationInfo				CN-InformationInfo					OPTIONAL,
	-- UTRAN mobility IEs
		ura-Identity					URA-Identity						OPTIONAL,
	-- Radio bearer IEs
		dl-CounterSynchronisationInfo	DL-CounterSynchronisationInfo-r5	OPTIONAL,
	-- Transport channel IEs
		ul-CommonTransChInfo			UL-CommonTransChInfo-r4				OPTIONAL,
		ul-AddReconfTransChInfoList		UL-AddReconfTransChInfoList			OPTIONAL,
		-- 'dummy', 'dummy1' and 'dummy2' are not used in this version of the specification,
		-- they should not be sent and if received they should be ignored.
		dummy							CHOICE {
			fdd								SEQUENCE {
				dummy1							CPCH-SetID					OPTIONAL,
				dummy2							DRAC-StaticInformationList	OPTIONAL
			},
			tdd								NULL
		}																	OPTIONAL,
		dl-CommonTransChInfo			DL-CommonTransChInfo-r4				OPTIONAL,
		dl-AddReconfTransChInfoList		DL-AddReconfTransChInfoList-r5		OPTIONAL,
	-- Physical channel IEs
		frequencyInfo					FrequencyInfo						OPTIONAL,
		maxAllowedUL-TX-Power			MaxAllowedUL-TX-Power				OPTIONAL,
		ul-ChannelRequirement			UL-ChannelRequirement-r5			OPTIONAL,
		modeSpecificPhysChInfo			CHOICE {
			fdd								SEQUENCE {
				-- dummy is not used in this version of specification, it should
				-- not be sent and if received it should be ignored.
				dummy							DL-PDSCH-Information		OPTIONAL
			},
			tdd							NULL
		},
		dl-HSPDSCH-Information			DL-HSPDSCH-Information				OPTIONAL,
		dl-CommonInformation			DL-CommonInformation-r5				OPTIONAL,
		dl-InformationPerRL-List		DL-InformationPerRL-List-r5			OPTIONAL
}

TransportChannelReconfiguration-v690ext-IEs ::= SEQUENCE {
	-- User Equipment IEs
		delayRestrictionFlag			DelayRestrictionFlag				OPTIONAL,
	-- Core network IEs
		primary-plmn-Identity			PLMN-Identity						OPTIONAL,
	-- Physical channel IEs
		-- The IE harq-Preamble-Mode should not be used in the r3 and r4 versions of the message
		-- If included in the r3 or r4 version of the message, the UE should ignore the IE
		harq-Preamble-Mode				HARQ-Preamble-Mode					OPTIONAL,
		beaconPLEst						BEACON-PL-Est						OPTIONAL,
		postVerificationPeriod			ENUMERATED { true }					OPTIONAL,
		dhs-sync						DHS-Sync							OPTIONAL,
		timingMaintainedSynchInd		TimingMaintainedSynchInd			OPTIONAL,
	-- MBMS IEs
		mbms-PL-ServiceRestrictInfo		MBMS-PL-ServiceRestrictInfo-r6		OPTIONAL
}

TransportChannelReconfiguration-r6-IEs ::= SEQUENCE {
	-- User equipment IEs
		integrityProtectionModeInfo		IntegrityProtectionModeInfo			OPTIONAL,
		cipheringModeInfo				CipheringModeInfo					OPTIONAL,
		activationTime					ActivationTime						OPTIONAL,
		delayRestrictionFlag			DelayRestrictionFlag				OPTIONAL,
		new-U-RNTI						U-RNTI								OPTIONAL,
		new-C-RNTI						C-RNTI								OPTIONAL,
		-- The IE "new-DSCH-RNTI" should not be included in FDD mode,
		-- and if received the UE behaviour is unspecified
		new-DSCH-RNTI					DSCH-RNTI							OPTIONAL,
		new-H-RNTI						H-RNTI								OPTIONAL,
		newPrimary-E-RNTI				E-RNTI								OPTIONAL,
		newSecondary-E-RNTI				E-RNTI								OPTIONAL,
		rrc-StateIndicator				RRC-StateIndicator,
		utran-DRX-CycleLengthCoeff		UTRAN-DRX-CycleLengthCoefficient	OPTIONAL,
	-- Core network IEs
		cn-InformationInfo				CN-InformationInfo-r6				OPTIONAL,
	-- UTRAN mobility IEs
		ura-Identity					URA-Identity						OPTIONAL,
	-- Radio bearer IEs
		dl-CounterSynchronisationInfo	DL-CounterSynchronisationInfo-r5	OPTIONAL,
	-- Transport channel IEs
		ul-CommonTransChInfo			UL-CommonTransChInfo-r4				OPTIONAL,
		ul-AddReconfTransChInfoList		UL-AddReconfTransChInfoList-r6		OPTIONAL,
		dl-CommonTransChInfo			DL-CommonTransChInfo-r4				OPTIONAL,
		dl-AddReconfTransChInfoList		DL-AddReconfTransChInfoList-r5		OPTIONAL,
	-- Physical channel IEs
		frequencyInfo					FrequencyInfo						OPTIONAL,
		maxAllowedUL-TX-Power			MaxAllowedUL-TX-Power				OPTIONAL,
		ul-DPCH-Info					UL-DPCH-Info-r6						OPTIONAL,
		ul-EDCH-Information				UL-EDCH-Information-r6				OPTIONAL,
		dl-HSPDSCH-Information			DL-HSPDSCH-Information-r6			OPTIONAL,
		dl-CommonInformation			DL-CommonInformation-r6				OPTIONAL,
		dl-InformationPerRL-List		DL-InformationPerRL-List-r6			OPTIONAL,
	-- MBMS IEs
		mbms-PL-ServiceRestrictInfo		MBMS-PL-ServiceRestrictInfo-r6		OPTIONAL
}

TransportChannelReconfiguration-v6b0ext-IEs ::= SEQUENCE {
	-- Physical channel IEs
		dl-InformationPerRL-List-v6b0ext	DL-InformationPerRL-List-v6b0ext	OPTIONAL
}

TransportChannelReconfiguration-r7-IEs ::= SEQUENCE {
	-- User equipment IEs
		integrityProtectionModeInfo		IntegrityProtectionModeInfo-r7		OPTIONAL,
		cipheringModeInfo				CipheringModeInfo-r7				OPTIONAL,
		activationTime					ActivationTime						OPTIONAL,
		delayRestrictionFlag			DelayRestrictionFlag				OPTIONAL,
		new-U-RNTI						U-RNTI								OPTIONAL,
		new-C-RNTI						C-RNTI								OPTIONAL,
		-- The IE "new-DSCH-RNTI" should not be included in FDD mode,
		-- and if received the UE behaviour is unspecified
		new-DSCH-RNTI					DSCH-RNTI							OPTIONAL,
		new-H-RNTI						H-RNTI								OPTIONAL,
		newPrimary-E-RNTI				E-RNTI								OPTIONAL,
		newSecondary-E-RNTI				E-RNTI								OPTIONAL,
		rrc-StateIndicator				RRC-StateIndicator,
		ueMobilityStateIndicator		High-MobilityDetected				OPTIONAL,
		utran-DRX-CycleLengthCoeff		UTRAN-DRX-CycleLengthCoefficient-r7	OPTIONAL,
	-- Core network IEs
		cn-InformationInfo				CN-InformationInfo-r6				OPTIONAL,
	-- UTRAN mobility IEs
		ura-Identity					URA-Identity						OPTIONAL,
		supportForChangeOfUE-Capability	BOOLEAN								OPTIONAL,
		responseToChangeOfUE-Capability	ENUMERATED { true }					OPTIONAL,
	-- Radio bearer IEs
		dl-CounterSynchronisationInfo	DL-CounterSynchronisationInfo-r5	OPTIONAL,
	-- Transport channel IEs
		ul-CommonTransChInfo			UL-CommonTransChInfo-r4				OPTIONAL,
		ul-AddReconfTransChInfoList		UL-AddReconfTransChInfoList-r7		OPTIONAL,
		dl-CommonTransChInfo			DL-CommonTransChInfo-r4				OPTIONAL,
		dl-AddReconfTransChInfoList		DL-AddReconfTransChInfoList-r7		OPTIONAL,
	-- Physical channel IEs
		frequencyInfo					FrequencyInfo						OPTIONAL,
		multi-frequencyInfo				Multi-frequencyInfo-LCR-r7			OPTIONAL,
		dtx-drx-TimingInfo				DTX-DRX-TimingInfo-r7				OPTIONAL,
		dtx-drx-Info					DTX-DRX-Info-r7						OPTIONAL,
		hs-scch-LessInfo				HS-SCCH-LessInfo-r7					OPTIONAL,
		mimoParameters					MIMO-Parameters-r7					OPTIONAL,
		maxAllowedUL-TX-Power			MaxAllowedUL-TX-Power				OPTIONAL,
		ul-DPCH-Info					UL-DPCH-Info-r7						OPTIONAL,
		ul-EDCH-Information				UL-EDCH-Information-r7				OPTIONAL,
		dl-HSPDSCH-Information			DL-HSPDSCH-Information-r7			OPTIONAL,
		dl-CommonInformation			DL-CommonInformation-r7				OPTIONAL,
		dl-InformationPerRL-List		DL-InformationPerRL-List-r7			OPTIONAL,
	-- MBMS IEs
		mbms-PL-ServiceRestrictInfo		MBMS-PL-ServiceRestrictInfo-r6		OPTIONAL
}

TransportChannelReconfiguration-v770ext-IEs ::= SEQUENCE {
	-- User equipment IEs
		ueMobilityStateIndicator		High-MobilityDetected				OPTIONAL
}

TransportChannelReconfiguration-v780ext-IEs ::= SEQUENCE {
	-- Physical channel IEs
		hs-DSCH-TBSizeTable				HS-DSCH-TBSizeTable					OPTIONAL
}

TransportChannelReconfiguration-v7d0ext-IEs ::= SEQUENCE {
	-- Physical channel IEs
		ul-EDCH-Information			UL-EDCH-Information-ext				OPTIONAL
}

TransportChannelReconfiguration-v7f0ext-IEs ::= SEQUENCE {
	-- Physical channel IEs
	mimoParameters						MIMO-Parameters-v7f0ext				OPTIONAL
}

TransportChannelReconfiguration-v7g0ext-IEs ::= SEQUENCE {
	-- Physical channel IEs
	mimoParameters						MIMO-Parameters-v7g0ext				OPTIONAL
}

TransportChannelReconfiguration-r8-IEs ::= SEQUENCE {
	-- User equipment IEs
		integrityProtectionModeInfo		IntegrityProtectionModeInfo-r7		OPTIONAL,
		cipheringModeInfo				CipheringModeInfo-r7				OPTIONAL,
		activationTime					ActivationTime						OPTIONAL,
		delayRestrictionFlag			DelayRestrictionFlag				OPTIONAL,
		new-U-RNTI						U-RNTI								OPTIONAL,
		new-C-RNTI						C-RNTI								OPTIONAL,
		-- The IE "new-DSCH-RNTI" should not be included in FDD mode,
		-- and if received the UE behaviour is unspecified
		new-DSCH-RNTI					DSCH-RNTI							OPTIONAL,
		new-H-RNTI						H-RNTI								OPTIONAL,
		newPrimary-E-RNTI				E-RNTI								OPTIONAL,
		newSecondary-E-RNTI				E-RNTI								OPTIONAL,
		rrc-StateIndicator				RRC-StateIndicator,
		ueMobilityStateIndicator		High-MobilityDetected				OPTIONAL,
		utran-DRX-CycleLengthCoeff		UTRAN-DRX-CycleLengthCoefficient-r7	OPTIONAL,
	-- Core network IEs
		cn-InformationInfo				CN-InformationInfo-r6				OPTIONAL,
	-- UTRAN mobility IEs
		ura-Identity					URA-Identity						OPTIONAL,
		supportForChangeOfUE-Capability	BOOLEAN								OPTIONAL,
		responseToChangeOfUE-Capability	ENUMERATED { true }					OPTIONAL,
	-- Radio bearer IEs
		dl-CounterSynchronisationInfo	DL-CounterSynchronisationInfo-r5	OPTIONAL,
	-- Transport channel IEs
		ul-CommonTransChInfo			UL-CommonTransChInfo-r4				OPTIONAL,
		ul-AddReconfTransChInfoList		UL-AddReconfTransChInfoList-r8		OPTIONAL,
		dl-CommonTransChInfo			DL-CommonTransChInfo-r4				OPTIONAL,
		dl-AddReconfTransChInfoList		DL-AddReconfTransChInfoList-r7		OPTIONAL,
	-- Physical channel IEs
		frequencyInfo					FrequencyInfo						OPTIONAL,
		multi-frequencyInfo				Multi-frequencyInfo-LCR-r7			OPTIONAL,
		dtx-drx-TimingInfo				DTX-DRX-TimingInfo-r7				OPTIONAL,
		dtx-drx-Info					DTX-DRX-Info-r7						OPTIONAL,
		hs-scch-LessInfo				HS-SCCH-LessInfo-r7					OPTIONAL,
		mimoParameters					MIMO-Parameters-r8					OPTIONAL,
		maxAllowedUL-TX-Power			MaxAllowedUL-TX-Power				OPTIONAL,
		ul-DPCH-Info					UL-DPCH-Info-r7						OPTIONAL,
		ul-EDCH-Information				UL-EDCH-Information-r8				OPTIONAL,
		dl-HSPDSCH-Information			DL-HSPDSCH-Information-r8			OPTIONAL,
		dl-CommonInformation			DL-CommonInformation-r8				OPTIONAL,
		dl-InformationPerRL-List		DL-InformationPerRL-List-r8			OPTIONAL,
		dl-SecondaryCellInfoFDD			DL-SecondaryCellInfoFDD				OPTIONAL,
		controlChannelDRXInfo-TDD128	ControlChannelDRXInfo-TDD128-r8		OPTIONAL,
		sps-Information-TDD128			SPS-Information-TDD128-r8			OPTIONAL,
	-- MBMS IEs
		mbms-PL-ServiceRestrictInfo		MBMS-PL-ServiceRestrictInfo-r6		OPTIONAL
}

TransportChannelReconfiguration-v890ext-IEs ::= SEQUENCE {
	-- Physical channel IEs
		dl-SecondaryCellInfoFDD-v890ext		DL-SecondaryCellInfoFDD-v890ext		OPTIONAL,
		dl-HSPDSCH-Information				DL-HSPDSCH-Information-r8-ext		OPTIONAL
}

TransportChannelReconfiguration-v8a0ext-IEs ::= SEQUENCE {
	-- Physical channel IEs
		dl-HSPDSCH-Information				DL-HSPDSCH-Information-r8-ext2		OPTIONAL
}

TransportChannelReconfiguration-r9-IEs ::= SEQUENCE {
	-- User equipment IEs
		integrityProtectionModeInfo		IntegrityProtectionModeInfo-r7		OPTIONAL,
		cipheringModeInfo				CipheringModeInfo-r7				OPTIONAL,
		activationTime					ActivationTime						OPTIONAL,
		delayRestrictionFlag			DelayRestrictionFlag				OPTIONAL,
		new-U-RNTI						U-RNTI								OPTIONAL,
		new-C-RNTI						C-RNTI								OPTIONAL,
		-- The IE "new-DSCH-RNTI" should not be included in FDD mode,
		-- and if received the UE behaviour is unspecified
		new-DSCH-RNTI					DSCH-RNTI							OPTIONAL,
		new-H-RNTI						H-RNTI								OPTIONAL,
		newPrimary-E-RNTI				E-RNTI								OPTIONAL,
		newSecondary-E-RNTI				E-RNTI								OPTIONAL,
		rrc-StateIndicator				RRC-StateIndicator,
		ueMobilityStateIndicator		High-MobilityDetected				OPTIONAL,
		utran-DRX-CycleLengthCoeff		UTRAN-DRX-CycleLengthCoefficient-r7	OPTIONAL,
	-- Core network IEs
		cn-InformationInfo				CN-InformationInfo-r6				OPTIONAL,
	-- UTRAN mobility IEs
		ura-Identity					URA-Identity						OPTIONAL,
		supportForChangeOfUE-Capability	BOOLEAN								OPTIONAL,
		responseToChangeOfUE-Capability	ENUMERATED { true }					OPTIONAL,
	-- Radio bearer IEs
		dl-CounterSynchronisationInfo	DL-CounterSynchronisationInfo-r5	OPTIONAL,
	-- Transport channel IEs
		ul-CommonTransChInfo			UL-CommonTransChInfo-r4				OPTIONAL,
		ul-AddReconfTransChInfoList		UL-AddReconfTransChInfoList-r8		OPTIONAL,
		dl-CommonTransChInfo			DL-CommonTransChInfo-r4				OPTIONAL,
		dl-AddReconfTransChInfoList		DL-AddReconfTransChInfoList-r9		OPTIONAL,
	-- Physical channel IEs
		frequencyInfo					FrequencyInfo						OPTIONAL,
		multi-frequencyInfo				Multi-frequencyInfo-LCR-r7			OPTIONAL,
		dtx-drx-TimingInfo				DTX-DRX-TimingInfo-r7				OPTIONAL,
		dtx-drx-Info					DTX-DRX-Info-r7						OPTIONAL,
		hs-scch-LessInfo				HS-SCCH-LessInfo-r7					OPTIONAL,
		mimoParameters					MIMO-Parameters-r9					OPTIONAL,
		maxAllowedUL-TX-Power			MaxAllowedUL-TX-Power				OPTIONAL,
		ul-DPCH-Info					UL-DPCH-Info-r7						OPTIONAL,
		ul-EDCH-Information				UL-EDCH-Information-r9				OPTIONAL,
		ul-SecondaryCellInfoFDD			UL-SecondaryCellInfoFDD				OPTIONAL,
		dl-HSPDSCH-Information			DL-HSPDSCH-Information-r9			OPTIONAL,
		dl-CommonInformation			DL-CommonInformation-r8				OPTIONAL,
		dl-InformationPerRL-List		DL-InformationPerRL-List-r8			OPTIONAL,
		dl-SecondaryCellInfoFDD			DL-SecondaryCellInfoFDD-r9			OPTIONAL,
		controlChannelDRXInfo-TDD128	ControlChannelDRXInfo-TDD128-r8		OPTIONAL,
		sps-Information-TDD128			SPS-Information-TDD128-r8			OPTIONAL,
	-- MBMS IEs
		mbms-PL-ServiceRestrictInfo		MBMS-PL-ServiceRestrictInfo-r6		OPTIONAL,
	-- Measurement IEs for LCR
		cellDCHMeasOccasionInfo-TDD128	CellDCHMeasOccasionInfo-TDD128-r9	OPTIONAL
}

TransportChannelReconfiguration-v950ext-IEs ::= SEQUENCE {
	-- Physical channel IEs
		secondaryCellMimoParameters		SecondaryCellMIMOparametersFDD-v950ext		OPTIONAL
}

TransportChannelReconfiguration-v9c0ext-IEs ::= SEQUENCE {
	-- For 1.28Mcps TDD only
		dl-AddReconfTransChInfoList		DL-AddReconfTransChInfoList-TDD128-v9c0ext			OPTIONAL
}

TransportChannelReconfiguration-r10-IEs ::= SEQUENCE {
	-- User equipment IEs
		integrityProtectionModeInfo		IntegrityProtectionModeInfo-r7		OPTIONAL,
		cipheringModeInfo				CipheringModeInfo-r7				OPTIONAL,
		activationTime					ActivationTime						OPTIONAL,
		delayRestrictionFlag			DelayRestrictionFlag				OPTIONAL,
		new-U-RNTI						U-RNTI								OPTIONAL,
		new-C-RNTI						C-RNTI								OPTIONAL,
		-- The IE "new-DSCH-RNTI" should not be included in FDD mode,
		-- and if received the UE behaviour is unspecified
		new-DSCH-RNTI					DSCH-RNTI							OPTIONAL,
		new-H-RNTI						H-RNTI								OPTIONAL,
		newPrimary-E-RNTI				E-RNTI								OPTIONAL,
		newSecondary-E-RNTI				E-RNTI								OPTIONAL,
		rrc-StateIndicator				RRC-StateIndicator,
		ueMobilityStateIndicator		High-MobilityDetected				OPTIONAL,
		utran-DRX-CycleLengthCoeff		UTRAN-DRX-CycleLengthCoefficient-r7	OPTIONAL,
	-- Core network IEs
		cn-InformationInfo				CN-InformationInfo-r6				OPTIONAL,
	-- UTRAN mobility IEs
		ura-Identity					URA-Identity						OPTIONAL,
		supportForChangeOfUE-Capability	BOOLEAN								OPTIONAL,
		responseToChangeOfUE-Capability	ENUMERATED { true }					OPTIONAL,
	-- Radio bearer IEs
		dl-CounterSynchronisationInfo	DL-CounterSynchronisationInfo-r5	OPTIONAL,
	-- Transport channel IEs
		ul-CommonTransChInfo			UL-CommonTransChInfo-r4				OPTIONAL,
		ul-AddReconfTransChInfoList		UL-AddReconfTransChInfoList-r8		OPTIONAL,
		dl-CommonTransChInfo			DL-CommonTransChInfo-r4				OPTIONAL,
		dl-AddReconfTransChInfoList		DL-AddReconfTransChInfoList-r9		OPTIONAL,
	-- Physical channel IEs
		frequencyInfo					FrequencyInfo						OPTIONAL,
		multi-frequencyInfo				Multi-frequencyInfo-LCR-r7			OPTIONAL,
		dtx-drx-TimingInfo				DTX-DRX-TimingInfo-r7				OPTIONAL,
		dtx-drx-Info					DTX-DRX-Info-r7						OPTIONAL,
		hs-scch-LessInfo				HS-SCCH-LessInfo-r7					OPTIONAL,
		mimoParameters					MIMO-Parameters-r9					OPTIONAL,
		maxAllowedUL-TX-Power			MaxAllowedUL-TX-Power				OPTIONAL,
		ul-DPCH-Info					UL-DPCH-Info-r7						OPTIONAL,
		ul-EDCH-Information				UL-EDCH-Information-r9				OPTIONAL,
		ul-SecondaryCellInfoFDD			UL-SecondaryCellInfoFDD				OPTIONAL,
		ul-MulticarrierEDCHInfo-TDD128	UL-MulticarrierEDCHInfo-TDD128		OPTIONAL,
		dl-HSPDSCH-Information			DL-HSPDSCH-Information-r9			OPTIONAL,
		dl-CommonInformation			DL-CommonInformation-r10			OPTIONAL,
		dl-InformationPerRL-List		DL-InformationPerRL-List-r8			OPTIONAL,
		dl-SecondaryCellInfoFDD			DL-SecondaryCellInfoFDD-r10			OPTIONAL,
		additionalDLSecCellInfoListFDD	AdditionalDLSecCellInfoListFDD		OPTIONAL,
		controlChannelDRXInfo-TDD128	ControlChannelDRXInfo-TDD128-r8		OPTIONAL,
		sps-Information-TDD128			SPS-Information-TDD128-r8			OPTIONAL,
		mu-MIMO-Info-TDD128				MU-MIMO-Info-TDD128					OPTIONAL,
	-- MBMS IEs
		mbms-PL-ServiceRestrictInfo		MBMS-PL-ServiceRestrictInfo-r6		OPTIONAL,
	-- Measurement IEs for LCR
		cellDCHMeasOccasionInfo-TDD128	CellDCHMeasOccasionInfo-TDD128-r9	OPTIONAL
}

TransportChannelReconfiguration-vb50ext-IEs ::= SEQUENCE {
		ulOLTDInfoFDD						UL-OLTD-InfoFDD			OPTIONAL
}

TransportChannelReconfiguration-r11-IEs ::= SEQUENCE {
	-- User equipment IEs
		integrityProtectionModeInfo		IntegrityProtectionModeInfo-r7		OPTIONAL,
		cipheringModeInfo				CipheringModeInfo-r7				OPTIONAL,
		activationTime					ActivationTime						OPTIONAL,
		delayRestrictionFlag			DelayRestrictionFlag				OPTIONAL,
		new-U-RNTI						U-RNTI								OPTIONAL,
		new-C-RNTI						C-RNTI								OPTIONAL,
		-- The IE "new-DSCH-RNTI" should not be included in FDD mode,
		-- and if received the UE behaviour is unspecified
		new-DSCH-RNTI					DSCH-RNTI							OPTIONAL,
		new-H-RNTI						H-RNTI								OPTIONAL,
		newPrimary-E-RNTI				E-RNTI								OPTIONAL,
		newSecondary-E-RNTI				E-RNTI								OPTIONAL,
		rrc-StateIndicator				RRC-StateIndicator,
		ueMobilityStateIndicator		High-MobilityDetected				OPTIONAL,
		utran-DRX-CycleLengthCoeff		UTRAN-DRX-CycleLengthCoefficient-r7	OPTIONAL,
	-- Core network IEs
		cn-InformationInfo				CN-InformationInfo-r6				OPTIONAL,
	-- UTRAN mobility IEs
		ura-Identity					URA-Identity						OPTIONAL,
		supportForChangeOfUE-Capability	BOOLEAN								OPTIONAL,
		responseToChangeOfUE-Capability	ENUMERATED { true }					OPTIONAL,
	-- Radio bearer IEs
		dl-CounterSynchronisationInfo	DL-CounterSynchronisationInfo-r5	OPTIONAL,
	-- Transport channel IEs
		ul-CommonTransChInfo			UL-CommonTransChInfo-r4				OPTIONAL,
		ul-AddReconfTransChInfoList		UL-AddReconfTransChInfoList-r8		OPTIONAL,
		dl-CommonTransChInfo			DL-CommonTransChInfo-r4				OPTIONAL,
		dl-AddReconfTransChInfoList		DL-AddReconfTransChInfoList-r11		OPTIONAL,
	-- Physical channel IEs
		frequencyInfo					FrequencyInfo						OPTIONAL,
		multi-frequencyInfo				Multi-frequencyInfo-LCR-r7			OPTIONAL,
		dtx-drx-TimingInfo				DTX-DRX-TimingInfo-r7				OPTIONAL,
		dtx-drx-Info					DTX-DRX-Info-r7						OPTIONAL,
		hs-scch-LessInfo				HS-SCCH-LessInfo-r7					OPTIONAL,
		mimoParameters					MIMO-Parameters-r9					OPTIONAL,
		mimo4x4Parameters				MIMO4x4-Parameters					OPTIONAL,
		maxAllowedUL-TX-Power			MaxAllowedUL-TX-Power				OPTIONAL,
		ul-DPCH-Info					UL-DPCH-Info-r11						OPTIONAL,
		ul-EDCH-Information				UL-EDCH-Information-r11				OPTIONAL,
		ul-SecondaryCellInfoFDD			UL-SecondaryCellInfoFDD				OPTIONAL,
		ul-MulticarrierEDCHInfo-TDD128	UL-MulticarrierEDCHInfo-TDD128		OPTIONAL,
		ul-CLTD-InfoFDD					UL-CLTD-InfoFDD						OPTIONAL,
		ul-OLTD-InfoFDD					UL-OLTD-InfoFDD						OPTIONAL,
		dl-HSPDSCH-Information			DL-HSPDSCH-Information-r11			OPTIONAL,
		dl-CommonInformation			DL-CommonInformation-r11			OPTIONAL,
		dl-InformationPerRL-List		DL-InformationPerRL-List-r11			OPTIONAL,
		dl-SecondaryCellInfoFDD			DL-SecondaryCellInfoFDD-r11			OPTIONAL,
		additionalDLSecCellInfoListFDD	AdditionalDLSecCellInfoListFDD-r11	OPTIONAL,
		additionalDLSecCellInfoListFDD2	AdditionalDLSecCellInfoListFDD2		OPTIONAL,
		commonERGCHInfoFDD				CommonERGCHInfoFDD					OPTIONAL,
		controlChannelDRXInfo-TDD128	ControlChannelDRXInfo-TDD128-r8		OPTIONAL,
		sps-Information-TDD128			SPS-Information-TDD128-r8			OPTIONAL,
		mu-MIMO-Info-TDD128				MU-MIMO-Info-TDD128					OPTIONAL,
	-- MBMS IEs
		mbms-PL-ServiceRestrictInfo		MBMS-PL-ServiceRestrictInfo-r6		OPTIONAL,
	-- Measurement IEs for LCR
		cellDCHMeasOccasionInfo-TDD128	CellDCHMeasOccasionInfo-TDD128-r9	OPTIONAL
}

-- ***************************************************
--
-- TRANSPORT CHANNEL RECONFIGURATION COMPLETE
--
-- ***************************************************

TransportChannelReconfigurationComplete ::= SEQUENCE {
	-- User equipment IEs
		rrc-TransactionIdentifier		RRC-TransactionIdentifier,
		ul-IntegProtActivationInfo		IntegrityProtActivationInfo			OPTIONAL,
		-- TABULAR: UL-TimingAdvance is applicable for TDD mode only.
		ul-TimingAdvance				UL-TimingAdvance					OPTIONAL,
	-- Radio bearer IEs
		count-C-ActivationTime			ActivationTime						OPTIONAL,
		-- dummy is not used in this version of the specification and
		-- it should be ignored by the receiver.
		dummy							RB-ActivationTimeInfoList			OPTIONAL,
		ul-CounterSynchronisationInfo	UL-CounterSynchronisationInfo		OPTIONAL,
		laterNonCriticalExtensions		SEQUENCE {
			-- Container for additional R99 extensions
			transportChannelReconfigurationComplete-r3-add-ext		BIT STRING		OPTIONAL,
			v770NonCriticalExtensions		SEQUENCE {
				transportChannelReconfigurationComplete-v770ext
										TransportChannelReconfigurationComplete-v770ext-IEs,
				nonCriticalExtensions			SEQUENCE {}		OPTIONAL
			}	OPTIONAL
		}	OPTIONAL
}

TransportChannelReconfigurationComplete-v770ext-IEs ::= SEQUENCE {
		-- TABULAR: EXT-UL-TimingAdvance is applicable for TDD mode only.
		ext-UL-TimingAdvance					EXT-UL-TimingAdvance	OPTIONAL,
		deferredMeasurementControlReading		ENUMERATED { true }		OPTIONAL
}

-- ***************************************************
--
-- TRANSPORT CHANNEL RECONFIGURATION FAILURE
--
-- ***************************************************

TransportChannelReconfigurationFailure ::= SEQUENCE {
	-- User equipment IEs
		rrc-TransactionIdentifier		RRC-TransactionIdentifier,
		failureCause					FailureCauseWithProtErr,
		laterNonCriticalExtensions			SEQUENCE {
			-- Container for additional R99 extensions
			transportChannelReconfigurationFailure-r3-add-ext		BIT STRING		OPTIONAL,
			nonCriticalExtensions			SEQUENCE {}		OPTIONAL
		}	OPTIONAL
}

-- *********************************************************
--
-- TRANSPORT FORMAT COMBINATION CONTROL in AM or UM RLC mode
--
-- *********************************************************

TransportFormatCombinationControl ::= SEQUENCE {
		-- rrc-TransactionIdentifier is always included in this version of the specification
		rrc-TransactionIdentifier		RRC-TransactionIdentifier			OPTIONAL,
		modeSpecificInfo					CHOICE {
			fdd									NULL,
			tdd									SEQUENCE {
				tfcs-ID								TFCS-Identity	OPTIONAL
			}	
		},
		dpch-TFCS-InUplink					TFC-Subset,
		activationTimeForTFCSubset			ActivationTime						OPTIONAL,
		tfc-ControlDuration					TFC-ControlDuration					OPTIONAL,
		laterNonCriticalExtensions			SEQUENCE {
			-- Container for additional R99 extensions
			transportFormatCombinationControl-r3-add-ext		BIT STRING		OPTIONAL,
			v820NonCriticalExtensions							SEQUENCE {
				transportformatcombinationcontrol-v820ext
													TransportFormatCombinationControl-v820ext-IEs,
				nonCriticalExtensions			SEQUENCE {}		OPTIONAL
			}	OPTIONAL
		}	OPTIONAL
}

TransportFormatCombinationControl-v820ext-IEs ::= SEQUENCE {
	-- Transport Format Combination Control IEs
		ul-AMR-Rate						UL-AMR-Rate								OPTIONAL
}

-- ***************************************************
--
-- TRANSPORT FORMAT COMBINATION CONTROL FAILURE
--
-- ***************************************************

TransportFormatCombinationControlFailure ::= SEQUENCE {
	-- User equipment IEs
		rrc-TransactionIdentifier		RRC-TransactionIdentifier,
		failureCause					FailureCauseWithProtErr,
		laterNonCriticalExtensions			SEQUENCE {
			-- Container for additional R99 extensions
			transportFormatCombinationControlFailure-r3-add-ext		BIT STRING		OPTIONAL,
			nonCriticalExtensions			SEQUENCE {}		OPTIONAL
		}	OPTIONAL
}

-- ***************************************************
--
-- UE CAPABILITY ENQUIRY
--
-- ***************************************************

UECapabilityEnquiry ::= CHOICE {
	r3								SEQUENCE {
		ueCapabilityEnquiry-r3			UECapabilityEnquiry-r3-IEs,
		laterNonCriticalExtensions		SEQUENCE {
			-- Container for additional R99 extensions
			ueCapabilityEnquiry-r3-add-ext		BIT STRING		OPTIONAL,
			v4b0NonCriticalExtensions		SEQUENCE { 
				ueCapabilityEnquiry-v4b0ext		UECapabilityEnquiry-v4b0ext-IEs,
				v590NonCriticalExtensions		SEQUENCE {
					ueCapabilityEnquiry-v590ext		UECapabilityEnquiry-v590ext-IEs,
					v770NonCriticalExtensions		SEQUENCE {
						ueCapabilityEnquiry-v770ext		UECapabilityEnquiry-v770ext-IEs,
						v860NonCriticalExtensions		SEQUENCE {
							ueCapabilityEnquiry-v860ext		UECapabilityEnquiry-v860ext-IEs,
							nonCriticalExtensions			SEQUENCE {}		OPTIONAL
						}	OPTIONAL
					}	OPTIONAL
				}	OPTIONAL
			}	OPTIONAL
		}	OPTIONAL
	},
	later-than-r3					SEQUENCE {
		rrc-TransactionIdentifier		RRC-TransactionIdentifier,
		criticalExtensions				SEQUENCE {}
	}
}

UECapabilityEnquiry-r3-IEs ::= SEQUENCE {
	-- User equipment IEs
		rrc-TransactionIdentifier		RRC-TransactionIdentifier,
		capabilityUpdateRequirement		CapabilityUpdateRequirement
}

UECapabilityEnquiry-v4b0ext-IEs ::= SEQUENCE {
		capabilityUpdateRequirement-r4-ext	CapabilityUpdateRequirement-r4-ext
}

UECapabilityEnquiry-v590ext-IEs ::= SEQUENCE {
		systemSpecificCapUpdateReq		SystemSpecificCapUpdateReq-v590ext
}

UECapabilityEnquiry-v770ext-IEs ::= SEQUENCE {
		capabilityUpdateRequirement		CapabilityUpdateRequirement-v770ext		OPTIONAL
}

UECapabilityEnquiry-v860ext-IEs ::= SEQUENCE {
		capabilityUpdateRequirement		CapabilityUpdateRequirement-v860ext		OPTIONAL
}

-- ***************************************************
--
-- UE CAPABILITY INFORMATION
--
-- ***************************************************

UECapabilityInformation ::= SEQUENCE {
	-- User equipment IEs
		rrc-TransactionIdentifier		RRC-TransactionIdentifier			OPTIONAL,
		ue-RadioAccessCapability		UE-RadioAccessCapability			OPTIONAL,
	-- Other IEs
		ue-RATSpecificCapability		InterRAT-UE-RadioAccessCapabilityList		OPTIONAL,
		v370NonCriticalExtensions			SEQUENCE {
			ueCapabilityInformation-v370ext	UECapabilityInformation-v370ext,
			v380NonCriticalExtensions			SEQUENCE {
				ueCapabilityInformation-v380ext		UECapabilityInformation-v380ext-IEs,
				v3a0NonCriticalExtensions			SEQUENCE {
					ueCapabilityInformation-v3a0ext		UECapabilityInformation-v3a0ext-IEs,
					laterNonCriticalExtensions			SEQUENCE {
						-- Container for additional R99 extensions
						ueCapabilityInformation-r3-add-ext		BIT STRING
									(CONTAINING UECapabilityInformation-r3-add-ext-IEs)	OPTIONAL,
						-- Reserved for future non critical extension
						v4b0NonCriticalExtensions			SEQUENCE {
							ueCapabilityInformation-v4b0ext		UECapabilityInformation-v4b0ext,
							v590NonCriticalExtensions			SEQUENCE {
								ueCapabilityInformation-v590ext		UECapabilityInformation-v590ext,
								v5c0NonCriticalExtensions			SEQUENCE {
									ueCapabilityInformation-v5c0ext
																	UECapabilityInformation-v5c0ext,
									v690NonCriticalExtensions			SEQUENCE {
										ueCapabilityInformation-v690ext
																UECapabilityInformation-v690ext-IEs,
										nonCriticalExtensions			SEQUENCE {}		OPTIONAL
									}		OPTIONAL
								}		OPTIONAL
							}		OPTIONAL
						}		OPTIONAL
					}		OPTIONAL
				}		OPTIONAL
			}		OPTIONAL
		}		OPTIONAL
}

UECapabilityInformation-v370ext ::= SEQUENCE {
	-- User equipment IEs
		ue-RadioAccessCapability-v370ext		UE-RadioAccessCapability-v370ext		OPTIONAL
}

UECapabilityInformation-v380ext-IEs ::= SEQUENCE {
	-- User equipment IEs
		ue-RadioAccessCapability-v380ext		UE-RadioAccessCapability-v380ext		OPTIONAL,
		dl-PhysChCapabilityFDD-v380ext			DL-PhysChCapabilityFDD-v380ext
}

UECapabilityInformation-v3a0ext-IEs ::= SEQUENCE {
	-- User equipment IEs
		ue-RadioAccessCapability-v3a0ext		UE-RadioAccessCapability-v3a0ext		OPTIONAL
}

UECapabilityInformation-r3-add-ext-IEs ::= SEQUENCE {
		ueCapabilityInformation-v650ext		UECapabilityInformation-v650ext-IEs		OPTIONAL,
		v680NonCriticalExtensions			SEQUENCE {
			ueCapabilityInformation-v680ext		UECapabilityInformation-v680ext-IEs,
			v7e0NonCriticalExtensions			SEQUENCE {
				ueCapabilityInformation-v7e0ext		UECapabilityInformation-v7e0ext-IEs,
				v7f0NonCriticalExtensions			SEQUENCE {
					ueCapabilityInformation-v7f0ext		UECapabilityInformation-v7f0ext-IEs,
					va40NonCriticalExtensions				SEQUENCE {
						ueCapabilityInformation-va40ext
															UECapabilityInformation-va40ext-IEs,
						nonCriticalExtensions				SEQUENCE {}	OPTIONAL 
					}		OPTIONAL
				}		OPTIONAL
			}		OPTIONAL
		}		OPTIONAL
}

UECapabilityInformation-v4b0ext ::= SEQUENCE {
	-- User equipment IEs
		ue-RadioAccessCapability-v4b0ext		UE-RadioAccessCapability-v4b0ext		OPTIONAL
}

UECapabilityInformation-v590ext ::= SEQUENCE {
	-- User equipment IEs
		ue-RadioAccessCapability-v3g0ext		UE-RadioAccessCapability-v3g0ext		OPTIONAL,
		ue-RadioAccessCapability-v590ext		UE-RadioAccessCapability-v590ext		OPTIONAL,
	-- Other IEs
		ue-RATSpecificCapability-v590ext	InterRAT-UE-RadioAccessCapability-v590ext	OPTIONAL
}

UECapabilityInformation-v5c0ext ::= SEQUENCE {
	-- User equipment IEs
		ue-RadioAccessCapability-v5c0ext		UE-RadioAccessCapability-v5c0ext		OPTIONAL
}

UECapabilityInformation-v650ext-IEs ::= SEQUENCE {
		ue-RadioAccessCapability-v650ext		UE-RadioAccessCapability-v650ext
}

UECapabilityInformation-v680ext-IEs ::= SEQUENCE {
	-- User equipment IEs
		ue-RadioAccessCapability-v680ext		UE-RadioAccessCapability-v680ext
}

UECapabilityInformation-v690ext-IEs ::= SEQUENCE {
	-- User equipment IEs
		ueCapabilityContainer				BIT STRING
												(CONTAINING UE-CapabilityContainer-IEs)	OPTIONAL
}

UECapabilityInformation-v7e0ext-IEs ::= SEQUENCE {
	-- User equipment IEs
		ue-RadioAccessCapability				UE-RadioAccessCapability-v7e0ext
}

UECapabilityInformation-v7f0ext-IEs ::= SEQUENCE {
	-- User equipment IEs
		ue-RadioAccessCapability				UE-RadioAccessCapability-v7f0ext	OPTIONAL
}

UECapabilityInformation-va40ext-IEs ::= SEQUENCE {
	-- User equipment IEs
		ue-RadioAccessCapabBand					UE-RadioAccessCapabBand-va40ext		OPTIONAL
}

-- ***************************************************
--
-- UE CAPABILITY INFORMATION CONFIRM
--
-- ***************************************************

UECapabilityInformationConfirm ::= CHOICE {
	r3								SEQUENCE {
		ueCapabilityInformationConfirm-r3
										UECapabilityInformationConfirm-r3-IEs,
		laterNonCriticalExtensions			SEQUENCE {
			-- Container for additional R99 extensions
			ueCapabilityInformationConfirm-r3-add-ext		BIT STRING		OPTIONAL,
			v770NonCriticalExtensions		SEQUENCE {
				ueCapabilityInformationConfirm-v770ext	UECapabilityInformationConfirm-v770ext-IEs,
				nonCriticalExtensions			SEQUENCE {}		OPTIONAL
			}	OPTIONAL
		}	OPTIONAL
	},
	later-than-r3					SEQUENCE {
		rrc-TransactionIdentifier		RRC-TransactionIdentifier,
		criticalExtensions				SEQUENCE {}
	}
}

UECapabilityInformationConfirm-r3-IEs ::= SEQUENCE {
	-- User equipment IEs
		rrc-TransactionIdentifier		RRC-TransactionIdentifier
}

UECapabilityInformationConfirm-v770ext-IEs ::= SEQUENCE {
	-- User equipment IEs
		acceptanceOfChangeOfCapability	ENUMERATED {
											refused, accepted, acceptedWithReconfigurationToFollow
										}		OPTIONAL
}

-- ***************************************************
--
-- UPLINK DIRECT TRANSFER
--
-- ***************************************************

UplinkDirectTransfer ::= SEQUENCE {
	-- Core network IEs
		cn-DomainIdentity				CN-DomainIdentity,
		nas-Message						NAS-Message,
	-- Measurement IEs
		measuredResultsOnRACH			MeasuredResultsOnRACH				OPTIONAL,
		laterNonCriticalExtensions			SEQUENCE {
			-- Container for additional R99 extensions
			uplinkDirectTransfer-r3-add-ext		BIT STRING		OPTIONAL,
			v690NonCriticalExtensions			SEQUENCE {
				uplinkDirectTransfer-v690ext		UplinkDirectTransfer-v690ext-IEs,
				v7g0NonCriticalExtensions			SEQUENCE {
					uplinkDirectTransfer-v7g0ext		UplinkDirectTransfer-v7g0ext-IEs,
					vb50NonCriticalExtensions		SEQUENCE {
						uplinkDirectTransfer-vb50ext	UplinkDirectTransfer-vb50ext-IEs,
						nonCriticalExtensions				SEQUENCE {}		OPTIONAL
					}	OPTIONAL
				}	OPTIONAL
			}	OPTIONAL
		}	OPTIONAL
}

UplinkDirectTransfer-v690ext-IEs ::= SEQUENCE {
	-- Measurement IEs
	measuredResultsOnRACHinterFreq		MeasuredResultsOnRACHinterFreq				OPTIONAL
}

UplinkDirectTransfer-v7g0ext-IEs ::=	SEQUENCE {
	-- Measurement IEs
		measuredResultsOnRACH-v7g0ext		MeasuredResultsOnRACH-v7g0ext		OPTIONAL
}

UplinkDirectTransfer-vb50ext-IEs ::=	SEQUENCE {
	-- Measurement IEs
	measuredResultsOnRACHEUTRAFreq		MeasuredResultsOnRACH-EUTRAFreq		OPTIONAL
}

-- ***************************************************
--
-- UPLINK PHYSICAL CHANNEL CONTROL
--
-- ***************************************************

UplinkPhysicalChannelControl ::= CHOICE {
	r3								SEQUENCE {
		uplinkPhysicalChannelControl-r3	UplinkPhysicalChannelControl-r3-IEs,
		laterNonCriticalExtensions			SEQUENCE {
			-- Container for additional R99 extensions
			uplinkPhysicalChannelControl-r3-add-ext		BIT STRING		OPTIONAL,
			v4b0NonCriticalExtensions		SEQUENCE {
				uplinkPysicalChannelControl-v4b0ext		UplinkPhysicalChannelControl-v4b0ext-IEs,
				-- Extension mechanism for non-release 4 information
				noncriticalExtensions			SEQUENCE {}						OPTIONAL
			}	OPTIONAL
		}	OPTIONAL
	},
	later-than-r3					SEQUENCE {
		rrc-TransactionIdentifier		RRC-TransactionIdentifier,
		criticalExtensions				CHOICE {
			r4								SEQUENCE {
				uplinkPhysicalChannelControl-r4	UplinkPhysicalChannelControl-r4-IEs,
				v4d0NonCriticalExtensions			SEQUENCE {
					-- Container for adding non critical extensions after freezing REL-5
					uplinkPhysicalChannelControl-r4-add-ext		BIT STRING		OPTIONAL,
					v690NonCriticalExtensions		SEQUENCE {
						uplinkPhysicalChannelControl-v690ext
														UplinkPhysicalChannelControl-v690ext-IEs,
						nonCriticalExtensions			SEQUENCE {}	OPTIONAL
					}	OPTIONAL
				}	OPTIONAL
			},
			criticalExtensions			CHOICE {
				r5								SEQUENCE {
					uplinkPhysicalChannelControl-r5	UplinkPhysicalChannelControl-r5-IEs,
					-- Container for adding non critical extensions after freezing REL-6
					uplinkPhysicalChannelControl-r5-add-ext		BIT STRING		OPTIONAL,
					v690NonCriticalExtensions		SEQUENCE {
						uplinkPhysicalChannelControl-v690ext
														UplinkPhysicalChannelControl-v690ext-IEs,
						v6a0NonCriticalExtensions		SEQUENCE{
							uplinkPhysicalChannelControl-v6a0ext
														UplinkPhysicalChannelControl-v6a0ext-IEs,
							nonCriticalExtensions			SEQUENCE {} OPTIONAL
						}	OPTIONAL
					}	OPTIONAL
				},
				criticalExtensions				CHOICE {
					r7								SEQUENCE {
						uplinkPhysicalChannelControl-r7	UplinkPhysicalChannelControl-r7-IEs,
						-- Container for adding non critical extensions after freezing REL-8
						uplinkPhysicalChannelControl-r7-add-ext		BIT STRING		OPTIONAL,
						nonCriticalExtensions			SEQUENCE {}		OPTIONAL
					},
					criticalExtensions				SEQUENCE {}
				}
			}
		}
	}
}

UplinkPhysicalChannelControl-r3-IEs ::= SEQUENCE {
	-- User equipment IEs
		rrc-TransactionIdentifier		RRC-TransactionIdentifier, 
	-- Physical channel IEs
		ccTrCH-PowerControlInfo			CCTrCH-PowerControlInfo				OPTIONAL,
		timingAdvance					UL-TimingAdvanceControl				OPTIONAL,
		alpha							Alpha								OPTIONAL,
		specialBurstScheduling			SpecialBurstScheduling				OPTIONAL,
		prach-ConstantValue				ConstantValueTdd					OPTIONAL,
		pusch-ConstantValue				ConstantValueTdd					OPTIONAL
}

UplinkPhysicalChannelControl-v4b0ext-IEs ::= SEQUENCE {
	-- In case of TDD, openLoopPowerControl-IPDL-TDD is included instead of IE
	-- up-IPDL-Parameters in up-OTDOA-AssistanceData
	openLoopPowerControl-IPDL-TDD	OpenLoopPowerControl-IPDL-TDD-r4	OPTIONAL
}

UplinkPhysicalChannelControl-r4-IEs ::= SEQUENCE {
	-- Physical channel IEs
		ccTrCH-PowerControlInfo			CCTrCH-PowerControlInfo-r4			OPTIONAL,
		specialBurstScheduling			SpecialBurstScheduling				OPTIONAL,
		tddOption						CHOICE {
			tdd384							SEQUENCE {
				timingAdvance					UL-TimingAdvanceControl-r4	OPTIONAL,
				alpha							Alpha						OPTIONAL,
				prach-ConstantValue				ConstantValueTdd			OPTIONAL,
				pusch-ConstantValue				ConstantValueTdd			OPTIONAL,
				openLoopPowerControl-IPDL-TDD	OpenLoopPowerControl-IPDL-TDD-r4	OPTIONAL
			},
			tdd128							SEQUENCE {
				ul-SynchronisationParameters	UL-SynchronisationParameters-r4	OPTIONAL
			}
		}
}

UplinkPhysicalChannelControl-r5-IEs ::= SEQUENCE {
	-- Physical channel IEs
		ccTrCH-PowerControlInfo			CCTrCH-PowerControlInfo-r5			OPTIONAL,
		specialBurstScheduling			SpecialBurstScheduling				OPTIONAL,
		tddOption						CHOICE {
			tdd384							SEQUENCE {
				timingAdvance					UL-TimingAdvanceControl-r4	OPTIONAL,
				alpha							Alpha						OPTIONAL,
				prach-ConstantValue				ConstantValueTdd			OPTIONAL,
				pusch-ConstantValue				ConstantValueTdd			OPTIONAL,
				openLoopPowerControl-IPDL-TDD	OpenLoopPowerControl-IPDL-TDD-r4	OPTIONAL,
				hs-SICH-PowerControl			HS-SICH-Power-Control-Info-TDD384	OPTIONAL
			},
			tdd128							SEQUENCE {
				ul-SynchronisationParameters	UL-SynchronisationParameters-r4	OPTIONAL
			}
		}
}

UplinkPhysicalChannelControl-v690ext-IEs ::= SEQUENCE {
	-- Physical Channel IEs
		beaconPLEst						BEACON-PL-Est						OPTIONAL
}

UplinkPhysicalChannelControl-v6a0ext-IEs ::= SEQUENCE {
	-- Physical Channel IEs
		desired-HS-SICH-PowerLevel		INTEGER (-120..-58)					OPTIONAL,
		tpc-Step-Size					ENUMERATED { s1, s2, s3 , spare1 }	OPTIONAL
}

UplinkPhysicalChannelControl-r7-IEs ::= SEQUENCE {
	-- Physical channel IEs
		ccTrCH-PowerControlInfo			CCTrCH-PowerControlInfo-r7			OPTIONAL,
		specialBurstScheduling			SpecialBurstScheduling				OPTIONAL,
		tddOption						CHOICE {
			tdd384							SEQUENCE {
				timingAdvance					UL-TimingAdvanceControl-r4	OPTIONAL,
				alpha							Alpha						OPTIONAL,
				prach-ConstantValue				ConstantValueTdd			OPTIONAL,
				pusch-ConstantValue				ConstantValueTdd			OPTIONAL,
				openLoopPowerControl-IPDL-TDD	OpenLoopPowerControl-IPDL-TDD-r4	OPTIONAL,
				hs-SICH-PowerControl			HS-SICH-Power-Control-Info-TDD384	OPTIONAL
			},
			tdd768							SEQUENCE {
				timingAdvance					UL-TimingAdvanceControl-r7	OPTIONAL,
				alpha							Alpha						OPTIONAL,
				prach-ConstantValue				ConstantValueTdd			OPTIONAL,
				pusch-ConstantValue				ConstantValueTdd			OPTIONAL,
				openLoopPowerControl-IPDL-TDD	OpenLoopPowerControl-IPDL-TDD-r4	OPTIONAL,
				hs-SICH-PowerControl			HS-SICH-Power-Control-Info-TDD768	OPTIONAL
			},
			tdd128							SEQUENCE {
				ul-SynchronisationParameters	UL-SynchronisationParameters-r4	OPTIONAL,
				desired-HS-SICH-PowerLevel		INTEGER (-120..-58)				OPTIONAL,
				tpc-Step-Size					ENUMERATED { s1, s2, s3 , spare1 }	OPTIONAL
			}
		}
}

-- ***************************************************
--
-- URA UPDATE
--
-- ***************************************************

URAUpdate ::= SEQUENCE {
	-- User equipment IEs
		u-RNTI							U-RNTI,
		ura-UpdateCause					URA-UpdateCause,
		protocolErrorIndicator			ProtocolErrorIndicatorWithMoreInfo,
		laterNonCriticalExtensions			SEQUENCE {
			-- Container for additional R99 extensions
			uraUpdate-r3-add-ext		BIT STRING
							(CONTAINING URAUpdate-r3-add-ext-IEs)		OPTIONAL,
			v770NonCriticalExtensions	SEQUENCE {
				uraUpdate-v770ext			UraUpdate-v770ext-IEs,
				v860NonCriticalExtensions	SEQUENCE {
					uraUpdate-v860ext			URAUpdate-v860ext-IEs,
					va40NonCriticalExtensions		SEQUENCE {
						uraUpdate-va40ext			URAUpdate-va40ext-IEs,
						nonCriticalExtensions 		SEQUENCE {} 	OPTIONAL
					}	OPTIONAL
				}	OPTIONAL
			}	OPTIONAL
		}	OPTIONAL
}

URAUpdate-r3-add-ext-IEs ::=		SEQUENCE {
	uraUpdate-v7e0ext					URAUpdate-v7e0ext-IEs,
	nonCriticalExtensions				SEQUENCE {}		OPTIONAL
}

UraUpdate-v770ext-IEs ::= SEQUENCE {
	-- User equipment IEs
	support-hsdschReception-CellUraPch		ENUMERATED { true }				OPTIONAL,
	support-hsdschReception-CellFach		ENUMERATED { true }				OPTIONAL
}

URAUpdate-v7e0ext-IEs ::=			SEQUENCE {
	-- User equipment IEs
		supportForTwoDRXSchemesInPCH		ENUMERATED { true }				OPTIONAL
}

URAUpdate-v860ext-IEs ::= SEQUENCE {
	-- User equipment IEs
	supportOfHS-DSCHDRXOperation			ENUMERATED { true }				OPTIONAL,
	supportOfCommonEDCH						ENUMERATED { true }				OPTIONAL,
	supportOfMACiis							ENUMERATED { true }				OPTIONAL
}

URAUpdate-va40ext-IEs ::= SEQUENCE {
	loggedMeasAvailable		ENUMERATED { true }	OPTIONAL,
	loggedANRResultsAvailable		ENUMERATED { true }		OPTIONAL
}

-- ***************************************************
--
-- URA UPDATE CONFIRM
--
-- ***************************************************

URAUpdateConfirm ::= CHOICE {
	r3								SEQUENCE {
		uraUpdateConfirm-r3				URAUpdateConfirm-r3-IEs,
		laterNonCriticalExtensions			SEQUENCE {
			-- Container for additional R99 extensions
			uraUpdateConfirm-r3-add-ext		BIT STRING		OPTIONAL,
			v690NonCriticalExtensions		SEQUENCE {
				uraUpdateConfirm-v690ext		URAUpdateConfirm-v690ext-IEs,
				nonCriticalExtensions			SEQUENCE {}		OPTIONAL
			}	OPTIONAL
		}	OPTIONAL
	},
	later-than-r3					SEQUENCE {
		rrc-TransactionIdentifier		RRC-TransactionIdentifier,
		criticalExtensions				CHOICE {
			r5								SEQUENCE {
				uraUpdateConfirm-r5				URAUpdateConfirm-r5-IEs,
				v690NonCriticalExtensions		SEQUENCE {
					uraUpdateConfirm-v690ext		URAUpdateConfirm-v690ext-IEs,
					nonCriticalExtensions			SEQUENCE {}		OPTIONAL
				}	OPTIONAL
			},
			criticalExtensions				CHOICE {
				r7								SEQUENCE {
					uraUpdateConfirm-r7				URAUpdateConfirm-r7-IEs,
					-- Container for adding non critical extensions after freezing REL-8
					uraUpdateConfirm-r7-add-ext		BIT STRING		OPTIONAL,
					v860NonCriticalExtensions		SEQUENCE {
						uraUpdateConfirm-v860ext		URAUpdateConfirm-v860ext-IEs,
						nonCriticalExtensions			SEQUENCE {}		OPTIONAL
					}	OPTIONAL
				},
				criticalExtensions				SEQUENCE {}
			}
		}
	}
}

URAUpdateConfirm-r3-IEs ::= SEQUENCE {
	-- User equipment IEs
		rrc-TransactionIdentifier		RRC-TransactionIdentifier, 
		integrityProtectionModeInfo		IntegrityProtectionModeInfo			OPTIONAL,
		cipheringModeInfo				CipheringModeInfo					OPTIONAL,
		new-U-RNTI						U-RNTI								OPTIONAL,
		new-C-RNTI						C-RNTI								OPTIONAL,
		rrc-StateIndicator				RRC-StateIndicator,
		utran-DRX-CycleLengthCoeff		UTRAN-DRX-CycleLengthCoefficient	OPTIONAL,
	-- CN information elements
		cn-InformationInfo				CN-InformationInfo					OPTIONAL,
	-- UTRAN mobility IEs
		ura-Identity					URA-Identity						OPTIONAL,
	-- Radio bearer IEs
		dl-CounterSynchronisationInfo	DL-CounterSynchronisationInfo		OPTIONAL
}

URAUpdateConfirm-r5-IEs ::= SEQUENCE {
	-- User equipment IEs
		integrityProtectionModeInfo		IntegrityProtectionModeInfo			OPTIONAL,
		cipheringModeInfo				CipheringModeInfo					OPTIONAL,
		new-U-RNTI						U-RNTI								OPTIONAL,
		new-C-RNTI						C-RNTI								OPTIONAL,
		rrc-StateIndicator				RRC-StateIndicator,
		utran-DRX-CycleLengthCoeff		UTRAN-DRX-CycleLengthCoefficient	OPTIONAL,
	-- CN information elements
		cn-InformationInfo				CN-InformationInfo					OPTIONAL,
	-- UTRAN mobility IEs
		ura-Identity					URA-Identity						OPTIONAL,
	-- Radio bearer IEs
		dl-CounterSynchronisationInfo	DL-CounterSynchronisationInfo-r5	OPTIONAL
}

URAUpdateConfirm-v690ext-IEs ::= SEQUENCE {
	-- Core network IEs
		primary-plmn-Identity				PLMN-Identity					OPTIONAL
}

URAUpdateConfirm-r7-IEs ::= SEQUENCE {
	-- User equipment IEs
		integrityProtectionModeInfo		IntegrityProtectionModeInfo-r7		OPTIONAL,
		cipheringModeInfo				CipheringModeInfo-r7				OPTIONAL,
		new-U-RNTI						U-RNTI								OPTIONAL,
		new-C-RNTI						C-RNTI								OPTIONAL,
		rrc-StateIndicator				RRC-StateIndicator,
		utran-DRX-CycleLengthCoeff		UTRAN-DRX-CycleLengthCoefficient-r7	OPTIONAL,
	-- CN information elements
		cn-InformationInfo				CN-InformationInfo					OPTIONAL,
		primary-plmn-Identity			PLMN-Identity						OPTIONAL,
	-- UTRAN mobility IEs
		ura-Identity					URA-Identity						OPTIONAL,
		supportForChangeOfUE-Capability	BOOLEAN								OPTIONAL,
	-- Radio bearer IEs
		dl-CounterSynchronisationInfo	DL-CounterSynchronisationInfo-r5	OPTIONAL
}

URAUpdateConfirm-v860ext-IEs ::= SEQUENCE {
	-- User equipment IEs
		new-H-RNTI						H-RNTI								OPTIONAL,
		newPrimary-E-RNTI				E-RNTI								OPTIONAL,
	-- Specification mode information
		-- dummy is not used in this version of the specification, it should
		-- not be sent and if received it should be ignored.
		dummy							DefaultConfigForCellFACH			OPTIONAL
}

-- ***************************************************
--
-- URA UPDATE CONFIRM for CCCH
--
-- ***************************************************

URAUpdateConfirm-CCCH ::= CHOICE {
	r3								SEQUENCE {
		uraUpdateConfirm-CCCH-r3		URAUpdateConfirm-CCCH-r3-IEs,
		laterNonCriticalExtensions			SEQUENCE {
			-- Container for additional R99 extensions
			uraUpdateConfirm-CCCH-r3-add-ext		BIT STRING		OPTIONAL,
			v690NonCriticalExtensions		SEQUENCE {
				uraUpdateConfirm-v690ext			URAUpdateConfirm-v690ext-IEs,
				v860NonCriticalExtensions		SEQUENCE {
					uraUpdateConfirm-v860ext		URAUpdateConfirm-v860ext-IEs,
					nonCriticalExtensions			SEQUENCE {}		OPTIONAL
				}	OPTIONAL
			}	OPTIONAL
		}	OPTIONAL
	},
	later-than-r3					SEQUENCE {
		u-RNTI							U-RNTI,
		rrc-TransactionIdentifier		RRC-TransactionIdentifier,
		criticalExtensions				SEQUENCE {}
	}
}

URAUpdateConfirm-CCCH-r3-IEs ::= SEQUENCE {
	-- User equipment IEs
		u-RNTI							U-RNTI,
	-- The rest of the message is identical to the one sent on DCCH.
		uraUpdateConfirm				URAUpdateConfirm-r3-IEs
}

-- ***************************************************
--
-- UTRAN MOBILITY INFORMATION
--
-- ***************************************************

UTRANMobilityInformation ::= CHOICE {
	r3								SEQUENCE {
		utranMobilityInformation-r3		UTRANMobilityInformation-r3-IEs,
		v3a0NonCriticalExtensions		SEQUENCE {
			utranMobilityInformation-v3a0ext	UTRANMobilityInformation-v3a0ext-IEs,
			laterNonCriticalExtensions			SEQUENCE {
				-- Container for additional R99 extensions
				utranMobilityInformation-r3-add-ext		BIT STRING		OPTIONAL,
				v690NonCriticalExtensions			SEQUENCE {
					utranMobilityInformation-v690ext	UtranMobilityInformation-v690ext-IEs,
					v860NonCriticalExtentions			SEQUENCE {
						utranMobilityInformation-v860ext	UTRANMobilityInformation-v860ext1-IEs,
						nonCriticalExtensions				SEQUENCE {}		OPTIONAL
					}		OPTIONAL
				}		OPTIONAL
			}		OPTIONAL
		}		OPTIONAL
	},
	later-than-r3					SEQUENCE {
		rrc-TransactionIdentifier		RRC-TransactionIdentifier,
		criticalExtensions				CHOICE {
			r5								SEQUENCE {
				utranMobilityInformation-r5		UTRANMobilityInformation-r5-IEs,
				v690NonCriticalExtensions		SEQUENCE {
					utranMobilityInformation-v690ext	UtranMobilityInformation-v690ext-IEs,
					v860NonCriticalExtentions			SEQUENCE {
						utranMobilityInformation-v860ext	UTRANMobilityInformation-v860ext1-IEs,
						nonCriticalExtensions			SEQUENCE {}		OPTIONAL
					}		OPTIONAL
				}	OPTIONAL
			},
			criticalExtensions					CHOICE {
				r7									SEQUENCE{
					utranMobilityInformation-r7			UTRANMobilityInformation-r7-IEs,
					-- Container for adding non critical extensions after freezing REL-8
					utranMobilityInformation-r7-add-ext	BIT STRING		OPTIONAL,
					v860NonCriticalExtensions			SEQUENCE {
						utranMobilityInformation-v860ext	UTRANMobilityInformation-v860ext2-IEs,
						vb50NonCriticalExtentions			SEQUENCE {
							utranMobilityInformation-vb50ext	
										UTRANMobilityInformation-vb50ext-IEs,
							nonCriticalExtensions				SEQUENCE {}		OPTIONAL
						}		OPTIONAL
					}		OPTIONAL
				},
				criticalExtensions					CHOICE {
					r11									SEQUENCE{
						utranMobilityInformation-r11		UTRANMobilityInformation-r11-IEs,
						-- Container for adding non critical extensions after freezing REL-12
						utranMobilityInformation-r11-add-ext	BIT STRING		OPTIONAL,
						nonCriticalExtensions				SEQUENCE {}		OPTIONAL
					},
					criticalExtensions				SEQUENCE {}
				}
			}
		}
	}
}

UTRANMobilityInformation-r3-IEs ::= SEQUENCE {
	-- User equipment IEs
		rrc-TransactionIdentifier		RRC-TransactionIdentifier, 
		integrityProtectionModeInfo		IntegrityProtectionModeInfo			OPTIONAL,
		cipheringModeInfo				CipheringModeInfo					OPTIONAL,
		new-U-RNTI						U-RNTI								OPTIONAL,
		new-C-RNTI						C-RNTI								OPTIONAL,
		ue-ConnTimersAndConstants		UE-ConnTimersAndConstants			OPTIONAL,
	-- CN information elements
		cn-InformationInfo				CN-InformationInfoFull				OPTIONAL,
	-- UTRAN mobility IEs
		ura-Identity					URA-Identity						OPTIONAL,
	-- Radio bearer IEs
		dl-CounterSynchronisationInfo	DL-CounterSynchronisationInfo		OPTIONAL,
	-- Extension mechanism for non- release99 information
		nonCriticalExtensions			SEQUENCE {}		OPTIONAL
}

UTRANMobilityInformation-v3a0ext-IEs ::= SEQUENCE {
	ue-ConnTimersAndConstants-v3a0ext		UE-ConnTimersAndConstants-v3a0ext
}

UTRANMobilityInformation-r5-IEs ::= SEQUENCE {
	-- User equipment IEs
		integrityProtectionModeInfo		IntegrityProtectionModeInfo			OPTIONAL,
		cipheringModeInfo				CipheringModeInfo					OPTIONAL,
		new-U-RNTI						U-RNTI								OPTIONAL,
		new-C-RNTI						C-RNTI								OPTIONAL,
		ue-ConnTimersAndConstants		UE-ConnTimersAndConstants-r5		OPTIONAL,
	-- CN information elements
		cn-InformationInfo				CN-InformationInfoFull				OPTIONAL,
	-- UTRAN mobility IEs
		ura-Identity					URA-Identity						OPTIONAL,
	-- Radio bearer IEs
		dl-CounterSynchronisationInfo	DL-CounterSynchronisationInfo-r5	OPTIONAL
}

UtranMobilityInformation-v690ext-IEs ::= SEQUENCE {
	-- Core network IEs
		primary-plmn-Identity				PLMN-Identity						OPTIONAL
}

UTRANMobilityInformation-r7-IEs ::= SEQUENCE {
	-- User equipment IEs
		integrityProtectionModeInfo		IntegrityProtectionModeInfo-r7		OPTIONAL,
		cipheringModeInfo				CipheringModeInfo-r7				OPTIONAL,
		new-U-RNTI						U-RNTI								OPTIONAL,
		new-C-RNTI						C-RNTI								OPTIONAL,
		new-H-RNTI						H-RNTI								OPTIONAL,
		ue-ConnTimersAndConstants		UE-ConnTimersAndConstants-r5		OPTIONAL,
	-- CN information elements
		cn-InformationInfo				CN-InformationInfoFull				OPTIONAL,
		primary-plmn-Identity			PLMN-Identity						OPTIONAL,
	-- UTRAN mobility IEs
		ura-Identity					URA-Identity						OPTIONAL,
		supportForChangeOfUE-Capability	BOOLEAN								OPTIONAL,
	-- Radio bearer IEs
		dl-CounterSynchronisationInfo	DL-CounterSynchronisationInfo-r5	OPTIONAL
}

UTRANMobilityInformation-v860ext1-IEs ::= SEQUENCE {
	-- User equipment IEs
	-- UE shall take into account the following ue-ConnTimersAndConstants
	-- only when ue-ConnTimersAndConstants IE is present in
	-- UTRANMobilityInformation-r3-IEs or UTRANMobilityInformation-r5-IEs.
	-- Otherwise, UE shall discard it.
		ue-ConnTimersAndConstants		UE-ConnTimersAndConstants-v860ext
}

UTRANMobilityInformation-v860ext2-IEs ::= SEQUENCE {
	-- User equipment IEs
		newPrimary-E-RNTI				E-RNTI								OPTIONAL,
	-- UE shall take into account the following ue-ConnTimersAndConstants
	-- only when ue-ConnTimersAndConstants IE is present in
	-- UTRANMobilityInformation-r7-IEs. Otherwise, UE shall discard it.
		ue-ConnTimersAndConstants		UE-ConnTimersAndConstants-v860ext,
	-- UTRAN Mobility IEs
		dedicatedPriorityInformation	DedicatedPriorityInformation		OPTIONAL
}

UTRANMobilityInformation-vb50ext-IEs ::= SEQUENCE {
	-- UTRAN Mobility IEs
		dedicatedPriorityInformation	DedicatedPriorityInformation-r11	OPTIONAL
}

UTRANMobilityInformation-r11-IEs ::= SEQUENCE {
	-- User equipment IEs
		integrityProtectionModeInfo		IntegrityProtectionModeInfo-r7		OPTIONAL,
		cipheringModeInfo				CipheringModeInfo-r7				OPTIONAL,
		new-U-RNTI						U-RNTI								OPTIONAL,
		new-C-RNTI						C-RNTI								OPTIONAL,
		new-H-RNTI						H-RNTI								OPTIONAL,
		newPrimary-E-RNTI				E-RNTI								OPTIONAL,
		ue-ConnTimersAndConstants		UE-ConnTimersAndConstants-r11		OPTIONAL,
	-- CN information elements
		cn-InformationInfo				CN-InformationInfoFull				OPTIONAL,
		primary-plmn-Identity			PLMN-Identity						OPTIONAL,
	-- UTRAN mobility IEs
		ura-Identity					URA-Identity						OPTIONAL,
		supportForChangeOfUE-Capability	BOOLEAN								OPTIONAL,
		dedicatedPriorityInformation	DedicatedPriorityInformation-r11	OPTIONAL,
	-- Radio bearer IEs
		dl-CounterSynchronisationInfo	DL-CounterSynchronisationInfo-r5	OPTIONAL
}

-- ***************************************************
--
-- UTRAN MOBILITY INFORMATION CONFIRM
--
-- ***************************************************

UTRANMobilityInformationConfirm ::= SEQUENCE {
	-- User equipment IEs
		rrc-TransactionIdentifier		RRC-TransactionIdentifier, 
		ul-IntegProtActivationInfo		IntegrityProtActivationInfo			OPTIONAL,
	-- Radio bearer IEs
		count-C-ActivationTime			ActivationTime						OPTIONAL,
		-- dummy is not used in this version of the specification and
		-- it should be ignored by the receiver.
		dummy							RB-ActivationTimeInfoList			OPTIONAL,
		ul-CounterSynchronisationInfo	UL-CounterSynchronisationInfo		OPTIONAL,
		laterNonCriticalExtensions			SEQUENCE {
			-- Container for additional R99 extensions
			utranMobilityInformationConfirm-r3-add-ext		BIT STRING		OPTIONAL,
			v770NonCriticalExtension			SEQUENCE {
				utranMobilityInformationConfirm-v770ext
													UTRANMobilityInformationConfirm-v770ext-IEs,
				va40NonCriticalExtensions				SEQUENCE {
					utranMobilityInformationConfirm-va40ext
														UTRANMobilityInformationConfirm-va40ext-IEs,
					nonCriticalExtensions				SEQUENCE {}		OPTIONAL
				}	OPTIONAL
			}	OPTIONAL
		}	OPTIONAL
}

UTRANMobilityInformationConfirm-v770ext-IEs ::= SEQUENCE {
	deferredMeasurementControlReading				ENUMERATED { true }		OPTIONAL
}

UTRANMobilityInformationConfirm-va40ext-IEs ::= SEQUENCE {
	loggedMeasAvailable				ENUMERATED { true }	OPTIONAL
}

-- ***************************************************
--
-- UTRAN MOBILITY INFORMATION FAILURE
--
-- ***************************************************

UTRANMobilityInformationFailure ::= SEQUENCE {
	-- UE information elements
		rrc-TransactionIdentifier		RRC-TransactionIdentifier, 
		failureCause					FailureCauseWithProtErr,
		laterNonCriticalExtensions			SEQUENCE {
			-- Container for additional R99 extensions
			utranMobilityInformationFailure-r3-add-ext		BIT STRING		OPTIONAL,
			nonCriticalExtensions			SEQUENCE {}		OPTIONAL
		}	OPTIONAL
}

-- ***************************************************
--
-- MBMS ACCESS INFORMATION
--
-- ***************************************************

MBMSAccessInformation ::= SEQUENCE {
	-- Access Information IEs
		mbms-ServiceAccessInfoList		MBMS-ServiceAccessInfoList-r6,
	-- Non critical extensions
		nonCriticalExtensions			SEQUENCE {}		OPTIONAL
}

-- ***************************************************
--
-- MBMS COMMON PTM RB INFORMATION
--
-- ***************************************************

MBMSCommonPTMRBInformation ::= SEQUENCE {
	-- Common PTM RB Information IEs
		mbms-CommonRBInformationList	MBMS-CommonRBInformationList-r6,
		mbms-TranspChInfoForEachTrCh	MBMS-TranspChInfoForEachTrCh-r6,
		mbms-TranspChInfoForEachCCTrCh	MBMS-TranspChInfoForEachCCTrCh-r6	OPTIONAL,
	-- For FDD and TDD 3.84Mcps in a cell operating in MBSFN only mode and for TDD 7.68Mcps the
	-- IE mbms-PhyChInformationList shall be ignored.
		mbms-PhyChInformationList		MBMS-PhyChInformationList-r6,
	-- Non critical extensions
		v770NonCriticalExtensions		SEQUENCE {
			mbmsCommonPTMRBInformation-v770ext
											MBMSCommonPTMRBInformation-v770ext-IEs,
			v780NonCriticalExtensions		SEQUENCE {
				mbmsCommonPTMRBInformation-v780ext
												MBMSCommonPTMRBInformation-v780ext-IEs,
				v860NonCriticalExtensions		SEQUENCE {
					mbmsCommonPTMRBInformation-v860ext
												MBMSCommonPTMRBInformation-v860ext-IEs,
					nonCriticalExtensions			SEQUENCE {}		OPTIONAL
				}		OPTIONAL
			}		OPTIONAL
		}		OPTIONAL
}

MBMSCommonPTMRBInformation-v770ext-IEs ::= SEQUENCE {
		-- TABULAR: CHOICE mode == "FDD or TDD"
		mbms-PhyChInformationList-r7	MBMS-PhyChInformationList-r7		OPTIONAL
}

MBMSCommonPTMRBInformation-v780ext-IEs ::= SEQUENCE {
		mbsfn-TDDInformation-LCR		MBSFN-TDDInformation-LCR			OPTIONAL
}

MBMSCommonPTMRBInformation-v860ext-IEs ::= SEQUENCE {
		-- TABULAR: CHOICE mode == "3.84 Mcps TDD IMB"
		mbms-PhyChInformationList		MBMS-PhyChInformationList-IMB384	OPTIONAL
}

-- ***************************************************
--
-- MBMS CURRENT CELL PTM RB INFORMATION
--
-- ***************************************************

MBMSCurrentCellPTMRBInformation ::= SEQUENCE {
	-- Current Cell PTM RB Information IEs
		mbms-CurrentCell-SCCPCHList		MBMS-CurrentCell-SCCPCHList-r6		OPTIONAL,
		mbms-SIBType5-SCCPCHList		MBMS-SIBType5-SCCPCHList-r6			OPTIONAL,
	-- Non critical extensions
		v770NonCriticalExtensions		SEQUENCE {
			mbmsCurrentCellPTMRBInfo-v770ext
											MBMSCurrentCellPTMRBInfo-v770ext-IEs,
			nonCriticalExtensions			SEQUENCE {}		OPTIONAL
		}		OPTIONAL
}

MBMSCurrentCellPTMRBInfo-v770ext-IEs ::= SEQUENCE {
		mbsfn-TDM-Info-List				MBSFN-TDM-Info-List					OPTIONAL
}

-- ***************************************************
--
-- MBMS GENERAL INFORMATION
--
-- ***************************************************

MBMSGeneralInformation ::= SEQUENCE {
	-- MBMS General Information IEs
		mbms-PreferredFrequencyInfo		MBMS-PreferredFrequencyList-r6		OPTIONAL,
		mbms-TimersAndCounters			MBMS-TimersAndCounters-r6,
		michConfigurationInfo			MBMS-MICHConfigurationInfo-r6,
		cellGroupIdentity				MBMS-CellGroupIdentity-r6,
		mschDefaultConfigurationInfo	MBMS-MSCH-ConfigurationInfo-r6		OPTIONAL,
	-- Non critical extensions
		v6b0NonCriticalExtensions		SEQUENCE {
			mbmsGeneralInformation-v6b0ext	MBMSGeneralInformation-v6b0ext-IEs,
			v770NonCriticalExtensions		SEQUENCE {
				mbmsGeneralInformation-v770ext	MBMSGeneralInformation-v770ext-IEs,
				v860NonCriticalExtensions		SEQUENCE {
					mbmsGeneralInformation-v860ext	MBMSGeneralInformation-v860ext-IEs,
						v890NoncriticalExtensions	SEQUENCE {
							mbmsGeneralInformation-v890ext	MBMSGeneralInformation-v890ext-IEs,
							nonCriticalExtensions			SEQUENCE {}		OPTIONAL
						}		OPTIONAL
				}		OPTIONAL
			}		OPTIONAL
		}		OPTIONAL
}

MBMSGeneralInformation-v6b0ext-IEs ::= SEQUENCE {
		indicateChangeInSelectedServices	BOOLEAN
}

MBMSGeneralInformation-v770ext-IEs ::= SEQUENCE {
		mbmsMICHConfiguration			MBMS-MICHConfigurationInfo-v770ext		OPTIONAL,
		mbsfnInterFrequencyNeighbourList
										MBSFN-InterFrequencyNeighbourList-r7	OPTIONAL
}

MBMSGeneralInformation-v860ext-IEs ::= SEQUENCE {
		mbsfnInterFrequencyNeighbourList
									MBSFN-InterFrequencyNeighbourList-v860ext	OPTIONAL
}

MBMSGeneralInformation-v890ext-IEs ::= SEQUENCE {
		mbmsNetworkStandardTimeInformation-LCR
									MBMS-NetworkStandardTimeInformation-LCR-v890ext	OPTIONAL,
		mbmsMICHConfiguration			MBMS-MICHConfigurationInfo-v890ext		OPTIONAL
}

-- ***************************************************
--
-- MBMS MODIFICATION REQUEST
--
-- ***************************************************

MBMSModificationRequest ::= SEQUENCE {
	-- MBMS Modification Request IEs
		mbms-PreferredFreqRequest		MBMS-ServiceIdentity-r6				OPTIONAL,
		rb-InformationReleaseList		RB-InformationReleaseList			OPTIONAL,
	-- Non critical extensions
		v6b0NonCriticalExtensions		SEQUENCE {
			mbmsModificationRequest-v6b0ext	MBMSModificationRequest-v6b0ext-IEs,
			v6f0NonCriticalExtensions		SEQUENCE {
				mbmsModificationRequest-v6f0ext	MBMSModificationRequest-v6f0ext-IEs,
				nonCriticalExtensions			SEQUENCE {}		OPTIONAL
			}		OPTIONAL
		}		OPTIONAL
}

MBMSModificationRequest-v6b0ext-IEs ::= SEQUENCE {
		mbmsSelectedServiceInfo			MBMS-SelectedServiceInfo
}

MBMSModificationRequest-v6f0ext-IEs ::= SEQUENCE {
		mbmsSupportOfServiceChangeForAPtpRB	ENUMERATED { true }				OPTIONAL
}

-- ***************************************************
--
-- MBMS MODIFIED SERVICES INFORMATION
--
-- ***************************************************

MBMSModifiedServicesInformation ::= SEQUENCE {
	-- MBMS Modified Services Information IEs
		modifedServiceList				MBMS-ModifedServiceList-r6			OPTIONAL,
		mbms-ReacquireMCCH				ENUMERATED { true }					OPTIONAL,
		mbms-DynamicPersistenceLevel	DynamicPersistenceLevel				OPTIONAL,
		endOfModifiedMCCHInformation	INTEGER (1..16)						OPTIONAL,
		mbmsNumberOfNeighbourCells		MBMS-NumberOfNeighbourCells-r6,
		mbms-AllUnmodifiedPTMServices	ENUMERATED { true }					OPTIONAL,
		mbms-PTMActivationTime			MBMS-PTMActivationTime-r6			OPTIONAL,
	-- Non critical extensions
		v770NonCriticalExtensions		SEQUENCE {
			mbmsModifiedServicesInformation-v770ext
											MBMSModifiedServicesInformation-v770ext-IEs,
			v7c0NonCriticalExtensions		SEQUENCE {
				mbmsModifiedServicesInformation-v7c0ext
												MBMSModifiedServicesInformation-v7c0ext-IEs,
				nonCriticalExtensions			SEQUENCE {}		OPTIONAL
			}		OPTIONAL
		}		OPTIONAL
}

MBMSModifiedServicesInformation-v770ext-IEs ::= SEQUENCE {
		modifiedServiceList				MBMS-ModifiedServiceList-v770ext	OPTIONAL,
		mib-ValueTag					MIB-ValueTag						OPTIONAL
}

MBMSModifiedServicesInformation-v7c0ext-IEs ::= SEQUENCE {
		modifiedServiceList				MBMS-ModifiedServiceList-LCR-v7c0ext	OPTIONAL
}

-- ***************************************************
--
-- MBMS NEIGHBOURING CELL PTM RB INFORMATION
--
-- ***************************************************

MBMSNeighbouringCellPTMRBInformation ::= SEQUENCE {
	-- MBMS Neighbouring Cell PTM RB Information IEs
		neighbouringCellIdentity		IntraFreqCellID,
		neighbouringCellSCCPCHList		MBMS-NeighbouringCellSCCPCHList-r6,
	-- Non critical extensions
		v770NonCriticalExtensions		SEQUENCE {
			mbmsNeighbouringCellPTMRBInformation-v770ext
											MBMSNeighbouringCellPTMRBInformation-v770ext-IEs,
			nonCriticalExtensions			SEQUENCE {}		OPTIONAL
		}		OPTIONAL
}

MBMSNeighbouringCellPTMRBInformation-v770ext-IEs ::= SEQUENCE {
	-- The "choice_PhyCH" in the tabular is realized by using the following IE due to the 
	-- constraint in the ASN.1 implementation.
		neighbouringCellSCCPCHList		MBMS-NeighbouringCellSCCPCHList-v770ext		OPTIONAL
}


-- ***************************************************
--
-- MBMS SCHEDULING INFORMATION
--
-- ***************************************************

MBMSSchedulingInformation ::= SEQUENCE {
	-- MBMS Scheduling Information IEs
		serviceSchedulingInfoList		MBMS-ServiceSchedulingInfoList-r6,
	-- Non critical extensions
		nonCriticalExtensions			SEQUENCE {}		OPTIONAL
}

-- ***************************************************
--
-- MBMS UNMODIFIED SERVICES INFORMATION
--
-- ***************************************************

MBMSUnmodifiedServicesInformation ::= SEQUENCE {
	-- MBMS Unmodified Services Information IEs
		unmodifiedServiceList			MBMS-UnmodifiedServiceList-r6		OPTIONAL,
	-- Non critical extensions
		v770NonCriticalExtensions		SEQUENCE {
			mbmsUnmodifiedServicesInformation-v770ext
											MBMSUnmodifiedServicesInformation-v770ext-IEs,
			nonCriticalExtensions			SEQUENCE {}		OPTIONAL
		}		OPTIONAL
}

MBMSUnmodifiedServicesInformation-v770ext-IEs ::= SEQUENCE {
		unmodifiedServiceList			MBMS-UnmodifiedServiceList-v770ext	OPTIONAL
}

-- ***************************************************
--
-- System Information Container
--
-- ***************************************************

System-Information-Container ::= SEQUENCE {
	mib									OCTET STRING (CONTAINING MasterInformationBlock),
	sysInfoTypeSB1						OCTET STRING (CONTAINING SysInfoTypeSB1)		OPTIONAL,
	sysInfoTypeSB2						OCTET STRING (CONTAINING SysInfoTypeSB2)		OPTIONAL,
	sysInfoType1						OCTET STRING (CONTAINING SysInfoType1),
	sysInfoType3						OCTET STRING (CONTAINING SysInfoType3),
	sysInfoType5						OCTET STRING (CONTAINING SysInfoType5),
	sysInfoType7						OCTET STRING (CONTAINING SysInfoType7),
	sysInfoType11						OCTET STRING (CONTAINING SysInfoType11)			OPTIONAL,
	sysInfoType11bis					OCTET STRING (CONTAINING SysInfoType11bis)		OPTIONAL,
	sysInfoType12						OCTET STRING (CONTAINING SysInfoType12)			OPTIONAL,
	vb50NonCriticalExtensions		SEQUENCE {
		system-Information-Container-vb50ext	System-Information-Container-vb50ext-IEs,
		nonCriticalExtensions				SEQUENCE {} 			OPTIONAL
	}	OPTIONAL
}

System-Information-Container-vb50ext-IEs ::=	SEQUENCE {
	sysInfoType22					OCTET STRING (CONTAINING SysInfoType22)			OPTIONAL
}

-- ***************************************************
--
-- LOGGING MEASUREMENT CONFIGURATION
--
-- ***************************************************

LoggingMeasurementConfiguration ::= SEQUENCE {
	rrc-TransactionIdentifier		RRC-TransactionIdentifier,
	criticalExtensions				CHOICE {
		r10						SEQUENCE {
			loggingMeasurementConfiguration-r10-IEs			LoggingMeasurementConfiguration-r10-IEs,
			-- Container for additional R10 extensions
			loggingMeasurementConfiguration-r10-add-ext		BIT STRING		OPTIONAL,
			nonCriticalExtensions	SEQUENCE {}		OPTIONAL
		},
		criticalExtensions				CHOICE {
			r11								SEQUENCE {
				loggingMeasurementConfiguration-r11-IEs		LoggingMeasurementConfiguration-r11-IEs,
				loggingMeasurementConfiguration-r11-add-ext		BIT STRING		OPTIONAL,
				nonCriticalExtensions	SEQUENCE {}		OPTIONAL
			},
			criticalExtensions			SEQUENCE {}
		}
	}
}

LoggingMeasurementConfiguration-r10-IEs ::= SEQUENCE {
	loggedMeasurementsConfigurationInfo		LoggedMeasurementsConfigurationInfo		OPTIONAL,
	loggedANRConfigurationInfo				LoggedANRConfigurationInfo				OPTIONAL
}

LoggingMeasurementConfiguration-r11-IEs ::= SEQUENCE {
	loggedMeasurementsConfigurationInfo		LoggedMeasurementsConfigurationInfo-r11		OPTIONAL,
	loggedANRConfigurationInfo				LoggedANRConfigurationInfo				OPTIONAL
}

-- ***************************************************
--
-- UE INFORMATION RESPONSE
--
-- ***************************************************

UEInformationResponse ::= SEQUENCE {
	rrc-TransactionIdentifier		RRC-TransactionIdentifier,
	loggedMeasReport				LoggedMeasReport			OPTIONAL,
	loggedANRReportInfoList			LoggedANRReportInfoList		OPTIONAL,
	vb50NonCriticalExtensions			SEQUENCE {
		ueInformationResponse-vb50ext	UEInformationResponse-vb50ext-IEs,
		nonCriticalExtensions			SEQUENCE {}			OPTIONAL
	}					OPTIONAL
}

UEInformationResponse-vb50ext-IEs ::= SEQUENCE {
	loggedMeasReport				LoggedMeasReport-vb50ext	OPTIONAL,
	connectionEstablishmentFailureReport	
									ConnectionEstablishmentFailureReport	OPTIONAL,
	loggedANRReportInfoList			LoggedANRReportInfoList-vb50ext				OPTIONAL
}

-- ***************************************************
--
-- UE INFORMATION REQUEST
--
-- ***************************************************

UEInformationRequest ::= SEQUENCE {
	rrc-TransactionIdentifier		RRC-TransactionIdentifier,
	criticalExtensions				CHOICE {
		r10						SEQUENCE {
			ueInformationRequest-r10				UEInformationRequest-r10-IEs,
			-- Container for additional R10 extensions
			ueInformationRequest-r10-add-ext		BIT STRING		OPTIONAL,
			nonCriticalExtensions	SEQUENCE {}		OPTIONAL
		},
		criticalExtensions				CHOICE {
			r11						SEQUENCE {
				ueInformationRequest-r11	UEInformationRequest-r11-IEs,
				-- Container for additional R11 extensions
				ueInformationRequest-r11-add-ext	BIT STRING		OPTIONAL,
				nonCriticalExtensions				SEQUENCE {}		OPTIONAL
			},
			criticalExtensions				SEQUENCE {}
		}
	}
}

UEInformationRequest-r10-IEs ::= SEQUENCE {
	loggedMeasReportRequest		ENUMERATED { true }	OPTIONAL,
	loggedANRReportRequest		ENUMERATED { true }	OPTIONAL
}

UEInformationRequest-r11-IEs ::= SEQUENCE {
	loggedMeasReportRequest		ENUMERATED { true }	OPTIONAL,
	loggedANRReportRequest		ENUMERATED { true }	OPTIONAL,
	connectionEstablishmentFailureRequest		ENUMERATED { true }	OPTIONAL
}

END
